string 	DOWNLOAD_URL 			= "http://eagle.berniwa.com/price.php";
//string 	DOWNLOAD_URL 			= "http://localhost/EaglePriceRequester/price.php";

string bomPricingTsv = "";
string bomPricingIds[];
int bomPricingIdCount = 0;

void bomPricingRequestStart()
{
	bomPricingTsv = "";
	bomPricingIdCount = 0;

	string headline[] = {"ID", "DISTRIBUTOR", "ORDER_NO", "QUANTITY", "PRICES", "PRICE", "AVAILABLE_QUANTITY", "PARTS_PER_PACKAGE", "MINIMUM_QUANTITY", "QUANTITY_MULTIPLIER", "DATASHEET"};
	sprintf(bomPricingTsv, "%s%s\n", bomPricingTsv,  strjoin(headline,'\t'));

}

void bomPricingRequestPartWithMultiplier(int part, int quantity)
{
	int found = 0;
	string id = distributor[part] + "-" + part_no[part];

	for(int i = 0; i < bomPricingIdCount; i++)
	{
		if(bomPricingIds[i] == id){found = 1; break;} 
	}

	if(!found)
	{
		string data[] = {
			distributor[part] + "-" + part_no[part], 
			distributor[part], order_no[part], "", 
			prices[part], price[part], available[part],
			per_pkg[part], min_qty[part], qty_mul[part],
			datasheet[part]
		};
		sprintf(data[3], "%d",  quantity * bomCountPartsWithSameOrderNo(distributor[part], order_no[part]));
		sprintf(bomPricingTsv, "%s%s\n", bomPricingTsv, strjoin(data,'\t'));	
		bomPricingIds[bomPricingIdCount] = id;
		bomPricingIdCount++;	
	}
}

void bomPricingRequestPart(int part)
{
	bomPricingRequestPartWithMultiplier(part, 1);
}

void bomPricingRequestDo()
{
	string lines[];
	int nlines = netpost(lines, DOWNLOAD_URL, "tsv=" + escapeString(bomPricingTsv));

	/*
	output("W:\\Hardware\\ulptest\\input.txt", "wt")
	{
		printf("%s", bomPricingTsv);
		//printf("%s", escapeString(bomPricingTsv));
	}	
	output("W:\\Hardware\\ulptest\\output.txt", "wt")
	{
		for(int i = 0; i < nlines; i++)
		{
			printf("%s\n", lines[i]);		
		}
	}
	*/
	lines[0] = "ID	DISTRIBUTOR	ORDER_NO	QUANTITY	PRICES	PRICE	AVAILABLE_QUANTITY	PARTS_PER_PACKAGE	MINIMUM_QUANTITY	QUANTITY_MULTIPLIER	DATASHEET";
	if(nlines >= 0)
	{
		for(int i = 0; i < partcount; i++)
		{
			string id = distributor[i] + "-" + part_no[i];
			if(lookup(lines, id, "ORDER_NO"))
			{
				price[i] 		= lookup(lines, id, "PRICE");
				prices[i] 		= lookup(lines, id, "PRICES");
				datasheet[i] 	= lookup(lines, id, "DATASHEET");
				available[i] 	= lookup(lines, id, "AVAILABLE_QUANTITY");
				per_pkg[i] 		= lookup(lines, id, "PARTS_PER_PACKAGE");
				min_qty[i] 		= lookup(lines, id, "MINIMUM_QUANTITY");
				qty_mul[i] 		= lookup(lines, id, "QUANTITY_MULTIPLIER");	
				bomUpdatePart(i, 10);				
			}
		}
	}
}


void bomPricingRequest(int part)
{
	bomPricingRequestStart();
	bomPricingRequestPart(part);
	bomPricingRequestDo();
}



void bomPricingRequestAllWithMultiplier(int quantity)
{
	bomPricingRequestStart();

	for(int i = 0; i < partcount; i++)
	{
		if(distributor[i] != "" && order_no[i] != "")
		{
			//dlgMessageBox("BomRequest"); 
			bomPricingRequestPartWithMultiplier(i, quantity);
		}
	}

	bomPricingRequestDo();
}

void bomPricingRequestAll()
{
	bomPricingRequestAllWithMultiplier(1);
}
