#include "boardsize.ulp"

getBoardSize();

string temp = "";

//u2mm
//i2mil
//mm2u

real maxX = u2mm(max_x);
real minX = u2mm(min_x);
real maxY = u2mm(max_y);
real minY = u2mm(min_y);

real x = maxX-minX;
real y = maxY-minY;

sprintf(temp, "WRITE;");

/*Check, if board fits in, if not, return Error message and don't run rest of ulp/create frame and stencil*/

if(x > 338 || x < 38 || y > 238 || y < 38){

   dlgMessageBox("Error! Board Size must be within: \n\n" + "x: 38mm - 338mm" + "\n" + "y: 38mm - 238mm"); 

   exit(0);
}
/*
sprintf(temp, "%s EDIT .sch;", temp); 

schematic(S){
	string schname = filesetext(S.name, "_ec.sch");
	sprintf(temp, "%s WRITE '%s';", temp, schname);
}

sprintf(temp, "%s EDIT .brd;", temp);
*/
/*
board(B){
	string brdname = filesetext(B.name, "_ec.brd");
	sprintf(temp, "%s WRITE '%s';", temp, brdname);
	sprintf(temp, "%s EDIT '%s';", temp, brdname);
}*/

sprintf(temp, "%s DISPLAY NONE;", temp);

sprintf(temp, "%s SET CONFIRM YES;", temp);

/*
Alle Layer außer dem Dimension-Layer ausblenden
Stärke auf 0.15mm ändern
Vorhandene Boardkanten auf 0.15mm ändern, falls zu schmal/breit
*/
sprintf(temp, "%s LAYER DIMENSION;", temp);
sprintf(temp, "%s CHANGE WIDTH 0.15mm;", temp);

sprintf(temp, "%s GROUP ALL;", temp);
sprintf(temp, "%s CHANGE WIDTH 0.15mm (>0 0);", temp);

// ================================================
//             Konturen Brechungsrahmen
// ================================================

real x_min_inline = minX-2;
real x_max_inline = maxX+2;
real y_min_inline = minY-2;
real y_max_inline = maxY+2;

/*Innenkante*/
sprintf(temp, "%s WIRE (%fmm %fmm) (%fmm %fmm) (%fmm %fmm) (%fmm %fmm) (%fmm %fmm);", temp, x_min_inline, y_min_inline, x_max_inline, y_min_inline, x_max_inline, y_max_inline, x_min_inline, y_max_inline, x_min_inline, y_min_inline);

real x_min_outline = x_min_inline -5;
real x_max_outline = x_max_inline +5;
real y_min_outline = y_min_inline -4;
real y_max_outline = y_max_inline +4;

/*Außenkante*/
sprintf(temp, "%s WIRE (%fmm %fmm) (%fmm %fmm) (%fmm %fmm) (%fmm %fmm) (%fmm %fmm);", temp, x_min_outline, y_min_outline, x_max_outline, y_min_outline, x_max_outline, y_max_outline, x_min_outline, y_max_outline, x_min_outline, y_min_outline);

// ===================
//        Fiducials
// ===================

real x_fiducial_left = x_min_inline - 2.5;
real x_fiducial_left_max = x_fiducial_left + 0.75;
real y_fiducial_top = y_max_inline + 1;
real y_fiducial_bot = y_min_inline -1;
real x_fiducial_right = x_max_inline + 2.5;
real x_fiducial_right_max = x_fiducial_right +0.75;

real x_fiducial_stop_left = x_fiducial_left - 1.5;
real x_fiducial_stop_right = x_fiducial_right +1.5;

// ===================
//        Top Fiducials
// ===================

sprintf(temp, "%s LAYER TOP;", temp);
sprintf(temp, "%s CHANGE WIDTH 0mm;", temp);

sprintf(temp, "%s CIRCLE (%fmm %fmm) (%fmm %fmm);", temp, x_fiducial_left, y_fiducial_top, x_fiducial_left_max, y_fiducial_top);
sprintf(temp, "%s CIRCLE (%fmm %fmm) (%fmm %fmm);", temp, x_fiducial_left, y_fiducial_bot, x_fiducial_left_max, y_fiducial_bot);
sprintf(temp, "%s CIRCLE (%fmm %fmm) (%fmm %fmm);", temp, x_fiducial_right, y_fiducial_top, x_fiducial_right_max, y_fiducial_top);
sprintf(temp, "%s CIRCLE (%fmm %fmm) (%fmm %fmm);", temp, x_fiducial_right, y_fiducial_bot, x_fiducial_right_max, y_fiducial_bot);

sprintf(temp, "%s LAYER TSTOP;", temp);
sprintf(temp, "%s CHANGE WIDTH 0mm;", temp);

sprintf(temp, "%s CIRCLE (%fmm %fmm) (%fmm %fmm);", temp, x_fiducial_left, y_fiducial_top, x_fiducial_stop_left, y_fiducial_top);
sprintf(temp, "%s CIRCLE (%fmm %fmm) (%fmm %fmm);", temp, x_fiducial_left, y_fiducial_bot, x_fiducial_stop_left, y_fiducial_bot);
sprintf(temp, "%s CIRCLE (%fmm %fmm) (%fmm %fmm);", temp, x_fiducial_right, y_fiducial_top, x_fiducial_stop_right, y_fiducial_top);
sprintf(temp, "%s CIRCLE (%fmm %fmm) (%fmm %fmm);", temp, x_fiducial_right, y_fiducial_bot, x_fiducial_stop_right, y_fiducial_bot);

// ===================
//        Bot Fiducials
// ===================

sprintf(temp, "%s LAYER BOTTOM;", temp);
sprintf(temp, "%s CHANGE WIDTH 0mm;", temp);

sprintf(temp, "%s CIRCLE (%fmm %fmm) (%fmm %fmm);", temp, x_fiducial_left, y_fiducial_top, x_fiducial_left_max, y_fiducial_top);
sprintf(temp, "%s CIRCLE (%fmm %fmm) (%fmm %fmm);", temp, x_fiducial_left, y_fiducial_bot, x_fiducial_left_max, y_fiducial_bot);
sprintf(temp, "%s CIRCLE (%fmm %fmm) (%fmm %fmm);", temp, x_fiducial_right, y_fiducial_top, x_fiducial_right_max, y_fiducial_top);
sprintf(temp, "%s CIRCLE (%fmm %fmm) (%fmm %fmm);", temp, x_fiducial_right, y_fiducial_bot, x_fiducial_right_max, y_fiducial_bot);

sprintf(temp, "%s LAYER BSTOP;", temp);
sprintf(temp, "%s CHANGE WIDTH 0mm;", temp);

sprintf(temp, "%s CIRCLE (%fmm %fmm) (%fmm %fmm);", temp, x_fiducial_left, y_fiducial_top, x_fiducial_stop_left, y_fiducial_top);
sprintf(temp, "%s CIRCLE (%fmm %fmm) (%fmm %fmm);", temp, x_fiducial_left, y_fiducial_bot, x_fiducial_stop_left, y_fiducial_bot);
sprintf(temp, "%s CIRCLE (%fmm %fmm) (%fmm %fmm);", temp, x_fiducial_right, y_fiducial_top, x_fiducial_stop_right, y_fiducial_top);
sprintf(temp, "%s CIRCLE (%fmm %fmm) (%fmm %fmm);", temp, x_fiducial_right, y_fiducial_bot, x_fiducial_stop_right, y_fiducial_bot);

// ===================
//        Stege
// ===================

sprintf(temp, "%s DISPLAY NONE;", temp);
sprintf(temp, "%s LAYER DIMENSION;", temp);
sprintf(temp, "%s CHANGE WIDTH 0.15mm;", temp);

void stege(){
	// ==============================
	//        Kanten der Stege
	// ==============================

	real steg_links_x_min = minX + (x/4)-1;
	real steg_links_x_max = minX + (x/4)+1;

	real steg_rechts_x_min = minX + ((x/2)+(x/4))-1;
	real steg_rechts_x_max = minX + ((x/2)+(x/4))+1;

	real steg_unten_y_min = minY + (y/4)-1;
	real steg_unten_y_max = minY + (y/4)+1;

	real steg_oben_y_min = minY + ((y/2)+(y/4))-1;
	real steg_oben_y_max = minY + ((y/2)+(y/4))+1;

	sprintf(temp, "%s WIRE (%fmm %fmm) (%fmm %fmm);", temp, minX, steg_oben_y_min, x_min_inline, steg_oben_y_min);
	sprintf(temp, "%s WIRE (%fmm %fmm) (%fmm %fmm);", temp, minX, steg_oben_y_max, x_min_inline, steg_oben_y_max);

	sprintf(temp, "%s WIRE (%fmm %fmm) (%fmm %fmm);", temp, minX, steg_unten_y_min, x_min_inline, steg_unten_y_min);
	sprintf(temp, "%s WIRE (%fmm %fmm) (%fmm %fmm);", temp, minX, steg_unten_y_max, x_min_inline, steg_unten_y_max);

	sprintf(temp, "%s WIRE (%fmm %fmm) (%fmm %fmm);", temp, steg_links_x_min, minY, steg_links_x_min, y_min_inline);
	sprintf(temp, "%s WIRE (%fmm %fmm) (%fmm %fmm);", temp, steg_links_x_max, minY, steg_links_x_max, y_min_inline);

	sprintf(temp, "%s WIRE (%fmm %fmm) (%fmm %fmm);", temp, steg_rechts_x_min, minY, steg_rechts_x_min, y_min_inline);
	sprintf(temp, "%s WIRE (%fmm %fmm) (%fmm %fmm);", temp, steg_rechts_x_max, minY, steg_rechts_x_max, y_min_inline);

	sprintf(temp, "%s WIRE (%fmm %fmm) (%fmm %fmm);", temp, maxX, steg_oben_y_min, x_max_inline, steg_oben_y_min);
	sprintf(temp, "%s WIRE (%fmm %fmm) (%fmm %fmm);", temp, maxX, steg_oben_y_max, x_max_inline, steg_oben_y_max);

	sprintf(temp, "%s WIRE (%fmm %fmm) (%fmm %fmm);", temp, maxX, steg_unten_y_min, x_max_inline, steg_unten_y_min);
	sprintf(temp, "%s WIRE (%fmm %fmm) (%fmm %fmm);", temp, maxX, steg_unten_y_max, x_max_inline, steg_unten_y_max);

	sprintf(temp, "%s WIRE (%fmm %fmm) (%fmm %fmm);", temp, steg_links_x_min, maxY, steg_links_x_min, y_max_inline);
	sprintf(temp, "%s WIRE (%fmm %fmm) (%fmm %fmm);", temp, steg_links_x_max, maxY, steg_links_x_max, y_max_inline);

	sprintf(temp, "%s WIRE (%fmm %fmm) (%fmm %fmm);", temp, steg_rechts_x_min, maxY, steg_rechts_x_min, y_max_inline);
	sprintf(temp, "%s WIRE (%fmm %fmm) (%fmm %fmm);", temp, steg_rechts_x_max, maxY, steg_rechts_x_max, y_max_inline);

	dlgMessageBox("Stege Created");
	// ================================================
	//             Verbindungslinien löschen
	// ================================================

	real x_viertel = minX + x/4;
	real y_viertel = minY + y/4;

	real x_dreiviertel = minX + (x/2)+ (x/4);
	real y_dreiviertel = minY + (y/2)+ (y/4);


	sprintf(temp, "%s DELETE (%fmm %fmm) (%fmm %fmm);", temp, minX, y_viertel, x_min_inline, y_viertel); 
	sprintf(temp, "%s DELETE (%fmm %fmm) (%fmm %fmm);", temp, minX, y_dreiviertel, x_min_inline, y_dreiviertel); 

	sprintf(temp, "%s DELETE (%fmm %fmm) (%fmm %fmm);", temp, maxX, y_viertel, x_max_inline, y_viertel); 
	sprintf(temp, "%s DELETE (%fmm %fmm) (%fmm %fmm);", temp, maxX, y_dreiviertel, x_max_inline, y_dreiviertel); 

	sprintf(temp, "%s DELETE (%fmm %fmm) (%fmm %fmm);", temp, x_viertel, minY, x_viertel, y_min_inline); 
	sprintf(temp, "%s DELETE (%fmm %fmm) (%fmm %fmm);", temp, x_dreiviertel, minY, x_dreiviertel, y_min_inline);

	sprintf(temp, "%s DELETE (%fmm %fmm) (%fmm %fmm);", temp, x_viertel, maxY, x_viertel, y_max_inline); 
	sprintf(temp, "%s DELETE (%fmm %fmm) (%fmm %fmm);", temp, x_dreiviertel, maxY, x_dreiviertel, y_max_inline); 

	// ================================================
	//             Kanten abrunden - Fräser
	// ================================================
	sprintf(temp, "%s MITER 1mm;", temp);

	/*Vertikal*/
	sprintf(temp, "%s MITER (%fmm %fmm);", temp, minX, steg_oben_y_min);
	sprintf(temp, "%s MITER (%fmm %fmm);", temp, minX, steg_oben_y_max);
	sprintf(temp, "%s MITER (%fmm %fmm);", temp, x_min_inline, steg_oben_y_min);
	sprintf(temp, "%s MITER (%fmm %fmm);", temp, x_min_inline, steg_oben_y_max);

	sprintf(temp, "%s MITER (%fmm %fmm);", temp, minX, steg_unten_y_min);
	sprintf(temp, "%s MITER (%fmm %fmm);", temp, minX, steg_unten_y_max);
	sprintf(temp, "%s MITER (%fmm %fmm);", temp, x_min_inline, steg_unten_y_min);
	sprintf(temp, "%s MITER (%fmm %fmm);", temp, x_min_inline, steg_unten_y_max);

	sprintf(temp, "%s MITER (%fmm %fmm);", temp, maxX, steg_oben_y_min);
	sprintf(temp, "%s MITER (%fmm %fmm);", temp, maxX, steg_oben_y_max);
	sprintf(temp, "%s MITER (%fmm %fmm);", temp, x_max_inline, steg_oben_y_min);
	sprintf(temp, "%s MITER (%fmm %fmm);", temp, x_max_inline, steg_oben_y_max);

	sprintf(temp, "%s MITER (%fmm %fmm);", temp, maxX, steg_unten_y_min);
	sprintf(temp, "%s MITER (%fmm %fmm);", temp, maxX, steg_unten_y_max);
	sprintf(temp, "%s MITER (%fmm %fmm);", temp, x_max_inline, steg_unten_y_min);
	sprintf(temp, "%s MITER (%fmm %fmm);", temp, x_max_inline, steg_unten_y_max);

	/*Horizontal*/
	sprintf(temp, "%s MITER (%fmm %fmm);", temp, steg_links_x_min, minY);
	sprintf(temp, "%s MITER (%fmm %fmm);", temp, steg_links_x_min, y_min_inline);
	sprintf(temp, "%s MITER (%fmm %fmm);", temp, steg_links_x_max, minY);
	sprintf(temp, "%s MITER (%fmm %fmm);", temp, steg_links_x_max, y_min_inline);

	sprintf(temp, "%s MITER (%fmm %fmm);", temp, steg_rechts_x_min, minY);
	sprintf(temp, "%s MITER (%fmm %fmm);", temp, steg_rechts_x_min, y_min_inline);
	sprintf(temp, "%s MITER (%fmm %fmm);", temp, steg_rechts_x_max, minY);
	sprintf(temp, "%s MITER (%fmm %fmm);", temp, steg_rechts_x_max, y_min_inline);

	sprintf(temp, "%s MITER (%fmm %fmm);", temp, steg_links_x_min, maxY);
	sprintf(temp, "%s MITER (%fmm %fmm);", temp, steg_links_x_min, y_max_inline);
	sprintf(temp, "%s MITER (%fmm %fmm);", temp, steg_links_x_max, maxY);
	sprintf(temp, "%s MITER (%fmm %fmm);", temp, steg_links_x_max, y_max_inline);

	sprintf(temp, "%s MITER (%fmm %fmm);", temp, steg_rechts_x_min, maxY);
	sprintf(temp, "%s MITER (%fmm %fmm);", temp, steg_rechts_x_min, y_max_inline);
	sprintf(temp, "%s MITER (%fmm %fmm);", temp, steg_rechts_x_max, maxY);
	sprintf(temp, "%s MITER (%fmm %fmm);", temp, steg_rechts_x_max, y_max_inline);

	/*Ecken*/
	sprintf(temp, "%s MITER (%fmm %fmm);", temp, x_min_inline, y_min_inline);
	sprintf(temp, "%s MITER (%fmm %fmm);", temp, x_max_inline, y_min_inline);
	sprintf(temp, "%s MITER (%fmm %fmm);", temp, x_min_inline, y_max_inline);
	sprintf(temp, "%s MITER (%fmm %fmm);", temp, x_max_inline, y_max_inline);

	
	// ==========================================
	//             Bohrungen Stege
	// ==========================================
	real x_bohrungen_links = minX+0.05;
	real x_bohrungen_rechts = maxX+0.05;
	real y_bohrungen_oben = maxY+0.05;
	real y_bohrungen_unten = minY+0.05;

	sprintf(temp, "%s CHANGE DRILL 0.35mm;", temp);

	real ybohrung1 = y_viertel+0.5;
	real ybohrung2 = y_viertel+1;
	real ybohrung3 = y_viertel+1.5;
	real ybohrung4 = y_viertel-0.5;
	real ybohrung5 = y_viertel-1;
	real ybohrung6 = y_viertel-1.5;

	real ybohrung7 = y_dreiviertel+0.5;
	real ybohrung8 = y_dreiviertel+1;
	real ybohrung9 = y_dreiviertel+1.5;
	real ybohrung10 = y_dreiviertel-0.5;
	real ybohrung11 = y_dreiviertel-1;
	real ybohrung12 = y_dreiviertel-1.5;

	/*
	for(int l = 0.2; l<=1.4; l+=0.4){
		
		real ybohrung_unten1 = y_viertel + l;
		real ybohrung_unten2 = y_viertel - l;
		real ybohrung_oben1 = y_dreiviertel + l;
		real ybohrung_oben2 = y_dreiviertel - l;
		sprintf(temp, "%s HOLE (%fmm %fmm);", temp, x_bohrungen_links, ybohrung_unten1);
		sprintf(temp, "%s HOLE (%fmm %fmm);", temp, x_bohrungen_links, ybohrung_unten2);
		sprintf(temp, "%s HOLE (%fmm %fmm);", temp, x_bohrungen_links, ybohrung_oben1);
		sprintf(temp, "%s HOLE (%fmm %fmm);", temp, x_bohrungen_links, ybohrung_oben2);
		
		sprintf(temp, "%s HOLE (%fmm %fmm);", temp, x_bohrungen_rechts, ybohrung_unten1);
		sprintf(temp, "%s HOLE (%fmm %fmm);", temp, x_bohrungen_rechts, ybohrung_unten2);
		sprintf(temp, "%s HOLE (%fmm %fmm);", temp, x_bohrungen_rechts, ybohrung_oben1);
		sprintf(temp, "%s HOLE (%fmm %fmm);", temp, x_bohrungen_rechts, ybohrung_oben2);
	}
	*/
	sprintf(temp, "%s HOLE (%fmm %fmm);", temp, x_bohrungen_links, ybohrung1);
	sprintf(temp, "%s HOLE (%fmm %fmm);", temp, x_bohrungen_links, ybohrung2);
	sprintf(temp, "%s HOLE (%fmm %fmm);", temp, x_bohrungen_links, ybohrung3);
	sprintf(temp, "%s HOLE (%fmm %fmm);", temp, x_bohrungen_links, ybohrung4);
	sprintf(temp, "%s HOLE (%fmm %fmm);", temp, x_bohrungen_links, ybohrung5);
	sprintf(temp, "%s HOLE (%fmm %fmm);", temp, x_bohrungen_links, ybohrung6);
	sprintf(temp, "%s HOLE (%fmm %fmm);", temp, x_bohrungen_links, y_viertel);
		 
	sprintf(temp, "%s HOLE (%fmm %fmm);", temp, x_bohrungen_rechts, ybohrung1);
	sprintf(temp, "%s HOLE (%fmm %fmm);", temp, x_bohrungen_rechts, ybohrung2);
	sprintf(temp, "%s HOLE (%fmm %fmm);", temp, x_bohrungen_rechts, ybohrung3);
	sprintf(temp, "%s HOLE (%fmm %fmm);", temp, x_bohrungen_rechts, ybohrung4);
	sprintf(temp, "%s HOLE (%fmm %fmm);", temp, x_bohrungen_rechts, ybohrung5);
	sprintf(temp, "%s HOLE (%fmm %fmm);", temp, x_bohrungen_rechts, ybohrung6);
	sprintf(temp, "%s HOLE (%fmm %fmm);", temp, x_bohrungen_rechts, y_viertel);

	sprintf(temp, "%s HOLE (%fmm %fmm);", temp, x_bohrungen_links, ybohrung7);
	sprintf(temp, "%s HOLE (%fmm %fmm);", temp, x_bohrungen_links, ybohrung8);
	sprintf(temp, "%s HOLE (%fmm %fmm);", temp, x_bohrungen_links, ybohrung9);
	sprintf(temp, "%s HOLE (%fmm %fmm);", temp, x_bohrungen_links, ybohrung10);
	sprintf(temp, "%s HOLE (%fmm %fmm);", temp, x_bohrungen_links, ybohrung11);
	sprintf(temp, "%s HOLE (%fmm %fmm);", temp, x_bohrungen_links, ybohrung12);
	sprintf(temp, "%s HOLE (%fmm %fmm);", temp, x_bohrungen_links, y_dreiviertel);
		 
	sprintf(temp, "%s HOLE (%fmm %fmm);", temp, x_bohrungen_rechts, ybohrung7);
	sprintf(temp, "%s HOLE (%fmm %fmm);", temp, x_bohrungen_rechts, ybohrung8);
	sprintf(temp, "%s HOLE (%fmm %fmm);", temp, x_bohrungen_rechts, ybohrung9);
	sprintf(temp, "%s HOLE (%fmm %fmm);", temp, x_bohrungen_rechts, ybohrung10);
	sprintf(temp, "%s HOLE (%fmm %fmm);", temp, x_bohrungen_rechts, ybohrung11);
	sprintf(temp, "%s HOLE (%fmm %fmm);", temp, x_bohrungen_rechts, ybohrung12);
	sprintf(temp, "%s HOLE (%fmm %fmm);", temp, x_bohrungen_rechts, y_dreiviertel);

	real xbohrung1 = x_viertel+0.5;
	real xbohrung2 = x_viertel+1;
	real xbohrung3 = x_viertel+1.5;
	real xbohrung4 = x_viertel-0.5;
	real xbohrung5 = x_viertel-1;
	real xbohrung6 = x_viertel-1.5;

	real xbohrung7 = x_dreiviertel+0.5;
	real xbohrung8 = x_dreiviertel+1;
	real xbohrung9 = x_dreiviertel+1.5;
	real xbohrung10 = x_dreiviertel-0.5;
	real xbohrung11 = x_dreiviertel-1;
	real xbohrung12 = x_dreiviertel-1.5;

	/*
	for(int m = 0.2; m<=1.4; m+=0.4){
		
		real xbohrung_links1 = x_viertel + m;
		real xbohrung_links2 = x_viertel - m;
		real xbohrung_rechts1 = x_dreiviertel + m;
		real xbohrung_rechts2 = x_dreiviertel - m;
		sprintf(temp, "%s HOLE (%f %f);", temp, xbohrung_links1, y_bohrungen_oben);
		sprintf(temp, "%s HOLE (%f %f);", temp, xbohrung_links2, y_bohrungen_oben);
		sprintf(temp, "%s HOLE (%f %f);", temp, xbohrung_rechts1, y_bohrungen_oben);
		sprintf(temp, "%s HOLE (%f %f);", temp, xbohrung_rechts2, y_bohrungen_oben);
		
		sprintf(temp, "%s HOLE (%f %f);", temp, xbohrung_links1, y_bohrungen_unten);
		sprintf(temp, "%s HOLE (%f %f);", temp, xbohrung_links2, y_bohrungen_unten);
		sprintf(temp, "%s HOLE (%f %f);", temp, xbohrung_rechts1, y_bohrungen_unten);
		sprintf(temp, "%s HOLE (%f %f);", temp, xbohrung_rechts2, y_bohrungen_unten);
	}
	*/

	sprintf(temp, "%s HOLE (%fmm %fmm);", temp, xbohrung1, y_bohrungen_oben);
	sprintf(temp, "%s HOLE (%fmm %fmm);", temp, xbohrung2, y_bohrungen_oben);
	sprintf(temp, "%s HOLE (%fmm %fmm);", temp, xbohrung3, y_bohrungen_oben);
	sprintf(temp, "%s HOLE (%fmm %fmm);", temp, xbohrung4, y_bohrungen_oben);
	sprintf(temp, "%s HOLE (%fmm %fmm);", temp, xbohrung5, y_bohrungen_oben);
	sprintf(temp, "%s HOLE (%fmm %fmm);", temp, xbohrung6, y_bohrungen_oben);
	sprintf(temp, "%s HOLE (%fmm %fmm);", temp, x_viertel, y_bohrungen_oben);

	sprintf(temp, "%s HOLE (%fmm %fmm);", temp, xbohrung7, y_bohrungen_oben);
	sprintf(temp, "%s HOLE (%fmm %fmm);", temp, xbohrung8, y_bohrungen_oben);
	sprintf(temp, "%s HOLE (%fmm %fmm);", temp, xbohrung9, y_bohrungen_oben);
	sprintf(temp, "%s HOLE (%fmm %fmm);", temp, xbohrung10, y_bohrungen_oben);
	sprintf(temp, "%s HOLE (%fmm %fmm);", temp, xbohrung11, y_bohrungen_oben);
	sprintf(temp, "%s HOLE (%fmm %fmm);", temp, xbohrung12, y_bohrungen_oben);
	sprintf(temp, "%s HOLE (%fmm %fmm);", temp, x_dreiviertel, y_bohrungen_oben);

	sprintf(temp, "%s HOLE (%fmm %fmm);", temp, xbohrung1, y_bohrungen_unten);
	sprintf(temp, "%s HOLE (%fmm %fmm);", temp, xbohrung2, y_bohrungen_unten);
	sprintf(temp, "%s HOLE (%fmm %fmm);", temp, xbohrung3, y_bohrungen_unten);
	sprintf(temp, "%s HOLE (%fmm %fmm);", temp, xbohrung4, y_bohrungen_unten);
	sprintf(temp, "%s HOLE (%fmm %fmm);", temp, xbohrung5, y_bohrungen_unten);
	sprintf(temp, "%s HOLE (%fmm %fmm);", temp, xbohrung6, y_bohrungen_unten);
	sprintf(temp, "%s HOLE (%fmm %fmm);", temp, x_viertel, y_bohrungen_unten);

	sprintf(temp, "%s HOLE (%fmm %fmm);", temp, xbohrung7, y_bohrungen_unten);
	sprintf(temp, "%s HOLE (%fmm %fmm);", temp, xbohrung8, y_bohrungen_unten);
	sprintf(temp, "%s HOLE (%fmm %fmm);", temp, xbohrung9, y_bohrungen_unten);
	sprintf(temp, "%s HOLE (%fmm %fmm);", temp, xbohrung10, y_bohrungen_unten);
	sprintf(temp, "%s HOLE (%fmm %fmm);", temp, xbohrung11, y_bohrungen_unten);
	sprintf(temp, "%s HOLE (%fmm %fmm);", temp, xbohrung12, y_bohrungen_unten);
	sprintf(temp, "%s HOLE (%fmm %fmm);", temp, x_dreiviertel, y_bohrungen_unten);
}

// =======================================
//             Stege einfügen
// =======================================
stege();

// =======================================
//             Drills Board
// =======================================
sprintf(temp, "%s LAYER HOLES;", temp);

/*Drills Circuit Board*/
real circuit_drill_x = minX-4.5;
real circuit_drill_y_min = minY+5;
real circuit_drill_y_max = maxY-5;

sprintf(temp, "%s CHANGE DRILL 3mm;", temp);
sprintf(temp, "%s HOLE (%fmm %fmm);", temp, circuit_drill_x, circuit_drill_y_min);
sprintf(temp, "%s HOLE (%fmm %fmm);", temp, circuit_drill_x, circuit_drill_y_max);


// =================================================
//             Außenkonturen Stencil
// =================================================
sprintf(temp, "%s CHANGE WIDTH 0;", temp);

real x_min_stencil = circuit_drill_x - 49;
real x_max_stencil = x_max_outline + 48.5;
real y_min_stencil = y_min_outline -20;
real y_max_stencil = y_max_outline +20;

sprintf(temp, "%s LAYER TCREAM;", temp);
sprintf(temp, "%s WIRE (%fmm %fmm) (%fmm %fmm) (%fmm %fmm) (%fmm %fmm) (%fmm %fmm);", temp, x_min_stencil, y_min_stencil, x_max_stencil, y_min_stencil, x_max_stencil, y_max_stencil, x_min_stencil, y_max_stencil, x_min_stencil, y_min_stencil);

sprintf(temp, "%s LAYER BCREAM;", temp);
sprintf(temp, "%s WIRE (%fmm %fmm) (%fmm %fmm) (%fmm %fmm) (%fmm %fmm) (%fmm %fmm);", temp, x_min_stencil, y_min_stencil, x_max_stencil, y_min_stencil, x_max_stencil, y_max_stencil, x_min_stencil, y_max_stencil, x_min_stencil, y_min_stencil);

// ========================================
//             Drills Stencil
// ========================================
/*
Drills als Circles auf tcream- und bcream-Layer
sonst vom Hersteller nicht berücksichtigt
tcream, bcream -> für Stencil
*/
sprintf(temp, "%s LAYER TCREAM;", temp);
sprintf(temp, "%s GRID mm 1;", temp);
sprintf(temp, "%s CHANGE WIDTH 0;", temp);

real stencil_drill_x_min =circuit_drill_x-30;
real stencil_drill_x_max = stencil_drill_x_min+2.65;

sprintf(temp, "%s CIRCLE (%fmm %fmm) (%fmm %fmm);", temp, stencil_drill_x_min, circuit_drill_y_min, stencil_drill_x_max, circuit_drill_y_min);
sprintf(temp, "%s CIRCLE (%fmm %fmm) (%fmm %fmm);", temp, stencil_drill_x_min, circuit_drill_y_max, stencil_drill_x_max, circuit_drill_y_max);

sprintf(temp, "%s LAYER BCREAM;", temp);

sprintf(temp, "%s CIRCLE (%fmm %fmm) (%fmm %fmm);", temp, stencil_drill_x_min, circuit_drill_y_min, stencil_drill_x_max, circuit_drill_y_min);
sprintf(temp, "%s CIRCLE (%fmm %fmm) (%fmm %fmm);", temp, stencil_drill_x_min, circuit_drill_y_max, stencil_drill_x_max, circuit_drill_y_max);

sprintf(temp, "%s WRITE;", temp);

exit(temp);
