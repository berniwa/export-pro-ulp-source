void bomOutputFarnellBom(string ofilename, real multi)
{
  output(ofilename, "w")
  {
    for (int i = 0;i < bomInfoCount; i++) 
    {
      if(strstr(bomAttributeDistributor[i], "farnell") >= 0)
      {
        printf("%s,%d\n", bomXMLSafe(bomAttributeOrderNo[i]), int(ceil(bomInfoPartCount[i] * multi)));
      }
    }    
  } 
}
