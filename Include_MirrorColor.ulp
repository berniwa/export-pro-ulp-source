/************************************************************/
/* HTLExportPro_Mirror.ulp                                  */
/* - Beschneidet Color BMP Images                           */
/************************************************************/
/* (c) Copyright 2011, Bernhard Wörndl-Aichriedler          */
/* xDevelop OG - Hardware Developer			*/
/* E-Mail: bwa@berniwa.com (bwa@xdevelop.at)                */
/* Homepage: www.berniwa.com (www.xdevelop.at)              */
/************************************************************/
/* Die Verwendung, das Kopieren bzw. die Weiterverbreitung  */
/* dieses ULP sind nur nach ausdrücklicher Erlaubnis des    */
/* Autors gestattet! 				*/
/************************************************************/
/* Letzte Änderung am 23.02.2011                            */
/* Version 1.0 (in ExportPro6)                            	*/
/************************************************************/

#include "Include_Misc.ulp";
string include_path = "Include_";

int BMP_bfOffBits = 10;
int BMP_biWidth 	= 18;
int BMP_biHeight	= 22;
int BMP_colorTableFirst = 0x36;

char bmpData[];
int bmpOffset = 0;
int bmpWidth = 0;
int bmpHeight = 0;
int bmpBlockSize = 0;

int bmpReadInt(int offset)
{
	int value = 0;
			
	for(int i = 0; i < 4; i++) 
	{
		value |= bmpData[offset + i] << (i*8);
	}

	return value;	
}

void bmpWriteInt(int bmpInt)
{

	int value = 0;
		
	for(int i = 0; i < 4; i++) 
	{
		printf("%c", (bmpInt >> (8*i)) & 0x000000FF);
	}	
}

void bmpConvert(string ifilename)
{
	string mstatus = "";
	sprintf(mstatus, "Mirroring image: %s - Gathering information ", ifilename);
	status(mstatus);


	int nBytes = fileread(bmpData, ifilename);

  
  	/*
  		Read status information
  	*/
  	bmpOffset = bmpReadInt(BMP_bfOffBits);
  	bmpWidth = bmpReadInt(BMP_biWidth);
  	bmpHeight = bmpReadInt(BMP_biHeight);

	/*
  		Calculate blocksize (24 bit RGB)
  	*/
	bmpBlockSize = ceil((24.0 * bmpWidth)/32.0)*4;


	
	output(ifilename, "wb")
	{	
  		string mstatus = "";
  		sprintf(mstatus, "Mirroring image: %s - Loading image information", ifilename);
  		status(mstatus);
  		
  		//Copy header
  		for(int i = 0; i < bmpOffset; i++)
  		{
  			printf("%c", bmpData[i]);	
  		}
  	
  		sprintf(mstatus, "Mirroring image: %s - Copying image data", ifilename);
  		status(mstatus);
  
  		
  		//Walk thru - line by line
  		
  		for(int line = 0; line < bmpHeight; line++)
  		{  	
  			sprintf(mstatus, "Mirroring image: %s - Finished %.0f%%", ifilename, (line*1.0/bmpHeight*100.0));
  			status(mstatus);
  			
			int offset = bmpOffset+line*bmpBlockSize;

			string xdata = "";
  			for(int byte = bmpWidth*3-1; byte > 0; byte-=3)
  			{
				xdata += bmpData[offset + byte-2];
				xdata += bmpData[offset + byte-1];
				xdata += bmpData[offset + byte];
			}
			for(int i = 0; i < bmpBlockSize - bmpWidth*3; i++)
			{
				xdata += '\x00';
			}

			printf(xdata);	
  		}

	}
}


if(OS_SIGNATURE == "Windows_7" || OS_SIGNATURE == "Windows_8" || OS_SIGNATURE == "Windows_10")	
{	
	string WinProgPath = getUlpDir("PNGMirrorCrop.exe");
	string Space = " ";
	string Param1 = "\"" + argv[1] + "\"";
	string Param2 = " 0 1";		//1st Method: <name> <crop> <mirror>
	string CallOfWinProg = WinProgPath + Space + Param1 + Param2;
	
  	//dlgMessageBox(argv[2]);
  	output(argv[2],"at"){
   	 	printf(CallOfWinProg+"\n");
  	}
}
else if(OS_SIGNATURE == "Linux")
{
	string WinProgPath = getUlpDir("LibPNGImage");
	system("chmod +x " + WinProgPath);	//getting execute-rights
	string Space = " ";
	string Param1 = "\"" + argv[1] + "\"";
	string Param2 = " 0 1";		//1st Method: <name> <crop> <mirror>
	string CallOfWinProg = WinProgPath + Space + Param1 + Param2;
	
  	//dlgMessageBox(argv[2]);
  	output(argv[2],"at"){
   	 	printf(CallOfWinProg+"\n");
  	}
}
else
{
	bmpConvert(argv[1]);
}
