#usage "<b>Change brd text sizes (of names and values)</b>\n"
       "<p>This script loops through all devices in a brd and changes the text size and ratio to new user specified values. "
       "<author>Bernhard Wörndl-Aichriedler (bwa@berniwa.com) - based on the ULP of rtzaudio@mindspring.com</author>"

string ulp_path = "";
string script_change = "";

int Result = 0;
string grid = "GRID MIL FINEST;\n";

// new text sizes/ratios in mils

real NamesSize    = 40;
int  NamesRatio   = 12;
int  NamesFont    = 1;
int  NamesAlign   = 0;

real ValuesSize   = 40;
int  ValuesRatio  = 8;
int  ValuesFont   = 1;
int  ValuesAlign   = 0;

int CorrectLayer = 0;

string Fonts[] = {"unchanged", "vector", "proportional","fixed"};
string Align[] = {"unchanged", "bottom left", "bottom center","bottom right", "top left", "top center","top right"};

string DoElement(UL_ELEMENT E) {

    real dx, dy;
    string temp = "";
    E.texts(T) {

        dx = u2mil(T.x);
        dy = u2mil(T.y);
	if(T.value == E.name)
	{
		if(NamesFont > 0)
		{
			sprintf(temp, "%s CHANGE FONT %s (%.3f %.3f);\n", temp, Fonts[NamesFont], dx, dy);
		}
		if(NamesAlign > 0)
		{
			sprintf(temp, "%s CHANGE ALIGN %s (%.3f %.3f);\n", temp, Align[NamesAlign], dx, dy);
		}
		if(u2mil(T.size) != NamesSize)
		{
			sprintf(temp, "%s CHANGE SIZE %.3f (%.3f %.3f);\n", temp, NamesSize, dx, dy);
		}
		if(T.ratio != NamesRatio)
		{
			sprintf(temp, "%s CHANGE RATIO %d (%.3f %.3f);\n", temp, NamesRatio, dx, dy);
		}
		
	}
	else if(T.value == E.value)
	{

		if(ValuesFont > 0)
		{
			sprintf(temp, "%s CHANGE FONT %s (%.3f %.3f);\n", temp, Fonts[ValuesFont], dx, dy);
		}
		if(ValuesAlign > 0)
		{
			sprintf(temp, "%s CHANGE ALIGN %s (%.3f %.3f);\n", temp, Align[ValuesAlign], dx, dy);
		}		
		if(u2mil(T.size) != ValuesSize)
		{
			sprintf(temp, "%s CHANGE SIZE %.3f (%.3f %.3f);\n", temp, ValuesSize, dx, dy);
		}
		if(T.ratio != ValuesRatio)
		{
			sprintf(temp, "%s CHANGE RATIO %d (%.3f %.3f);\n", temp, ValuesRatio, dx, dy);
		}

	}
    }
    return temp;
}


void menue(void) {
   int err = 0;
   int newWidth;
   int minLimit = 0;
   int maxLimit = 0;

   dlgDialog("Change All Text Sizes/Ratios") {
          dlgGroup("tNames Text") {
             dlgHBoxLayout {   dlgLabel("New size (2-100 mils) :\t"); dlgRealEdit(NamesSize, 10.0, 100.0);   }
             dlgHBoxLayout {   dlgLabel("New ratio  (8-20%) :\t"); 	dlgIntEdit(NamesRatio, 8, 20);   }
             dlgHBoxLayout {   dlgLabel("New font:\t"); 		dlgComboBox(Fonts, NamesFont);   }
             dlgHBoxLayout {   dlgLabel("New alignment:\t"); 	dlgComboBox(Align, NamesAlign);   }
          }
          dlgGroup("tValues Text") {
             dlgHBoxLayout {   dlgLabel("New size (2-100 mils) :\t"); dlgRealEdit(ValuesSize, 10.0, 100.0);   }
             dlgHBoxLayout {   dlgLabel("New ratio (8-20%) :\t"); 	dlgIntEdit(ValuesRatio, 8, 20);   }
             dlgHBoxLayout {   dlgLabel("New font:\t"); 		dlgComboBox(Fonts, ValuesFont);   }
             dlgHBoxLayout {   dlgLabel("New alignment:\t"); 	dlgComboBox(Align, ValuesAlign);   }
          }
	
	dlgGroup("Correct layers")
	{
		dlgCheckBox("&Correct Layers according to >Name & >Value", CorrectLayer);
	}
      dlgPushButton("+&OK") { dlgAccept(); return; }
      dlgPushButton("-&Cancel") { dlgReject(); exit (0);}
   };
}

if(board) {

  string cmd = "";
  board(B) {
	
   	menue();
	cmd = "GRID mil; \n";
	B.elements(E)
	{
		cmd += DoElement(E);
   	}
	cmd += "GRID LAST; \n";
dlgMessageBox(cmd);
  }
  exit (cmd);
} else {
   dlgMessageBox("\n*** Start this ULP in a PCB Editor***\n");
   exit (0);
}
