#usage "<b>Change lib text sizes (of symbols)</b>\n"
       "<p>This script loops through all symbols in a library and changes the text size and ratio to new user specified values. "
       "<author>Bernhard Wörndl-Aichriedler (bwa@berniwa.com) - based on the ULP of rtzaudio@mindspring.com</author>"

string ulp_path = "";
string script_change = "";

int Result = 0;
string grid = "GRID MIL FINEST;\n";

// new text sizes/ratios in mils

real NamesSize    = 60;
int  NamesRatio   = 8;
int  NamesFont    = 0;
int  NamesAlign   = 0;

real ValuesSize   = 50;
int  ValuesRatio  = 8;
int  ValuesFont   = 0;
int  ValuesAlign   = 0;

int CorrectLayer = 0;

string Fonts[] = {"unchanged", "vector", "proportional","fixed"};
string Align[] = {"unchanged", "bottom left", "bottom center","bottom right", "top left", "top center","top right"};

void DoPackage(UL_SYMBOL S) {

    real dx, dy;

    S.texts(T) {
        dx = u2mil(T.x);
        dy = u2mil(T.y);
	if(strlwr(T.value) == ">name")
	{
		printf("CHANGE SIZE %.3f (%.3f %.3f);\n", NamesSize, dx, dy);
		printf("CHANGE RATIO %d (%.3f %.3f);\n", NamesRatio, dx, dy);

		if(NamesFont > 0)
		{
			printf("CHANGE FONT %s (%.3f %.3f);\n", Fonts[NamesFont], dx, dy);
		}
		if(NamesAlign > 0)
		{
			printf("CHANGE ALIGN %s (%.3f %.3f);\n", Align[NamesAlign], dx, dy);
		}


		if(CorrectLayer)
		{
			printf("CHANGE LAYER 95 (%.3f %.3f);\n", dx, dy);	
		}		
	}
	else if(strlwr(T.value) == ">value")
	{
		printf("CHANGE SIZE %.3f (%.3f %.3f);\n", ValuesSize, dx, dy);
		printf("CHANGE RATIO %d (%.3f %.3f);\n", ValuesRatio, dx, dy);

		if(ValuesFont > 0)
		{
			printf("CHANGE FONT %s (%.3f %.3f);\n", Fonts[ValuesFont], dx, dy);
		}
		if(ValuesAlign > 0)
		{
			printf("CHANGE ALIGN %s (%.3f %.3f);\n", Align[ValuesAlign], dx, dy);
		}

		if(CorrectLayer)
		{
			printf("CHANGE LAYER 96 (%.3f %.3f);\n", dx, dy);
		}
	}
/*
	if (T.layer == 95) {
            // Change tNames layer text

        } else if (T.layer == 96) {
            // Change tValues layer text
        }
*/
    }
}


void menue(void) {
   int err = 0;
   int newWidth;
   int minLimit = 0;
   int maxLimit = 0;

   dlgDialog("Change All Text Sizes/Ratios") {
          dlgGroup("tNames Text") {
             dlgHBoxLayout {   dlgLabel("New size (2-100 mils) :\t"); dlgRealEdit(NamesSize, 10.0, 100.0);   }
             dlgHBoxLayout {   dlgLabel("New ratio  (8-20%) :\t"); 	dlgIntEdit(NamesRatio, 8, 20);   }
             dlgHBoxLayout {   dlgLabel("New font:\t"); 		dlgComboBox(Fonts, NamesFont);   }
             dlgHBoxLayout {   dlgLabel("New alignment:\t"); 	dlgComboBox(Align, NamesAlign);   }
          }
          dlgGroup("tValues Text") {
             dlgHBoxLayout {   dlgLabel("New size (2-100 mils) :\t"); dlgRealEdit(ValuesSize, 10.0, 100.0);   }
             dlgHBoxLayout {   dlgLabel("New ratio (8-20%) :\t"); 	dlgIntEdit(ValuesRatio, 8, 20);   }
             dlgHBoxLayout {   dlgLabel("New font:\t"); 		dlgComboBox(Fonts, ValuesFont);   }
             dlgHBoxLayout {   dlgLabel("New alignment:\t"); 	dlgComboBox(Align, ValuesAlign);   }
          }
	
	dlgGroup("Correct layers")
	{
		dlgCheckBox("&Correct Layers according to >Name & >Value", CorrectLayer);
	}
      dlgPushButton("+&OK") { dlgAccept(); return; }
      dlgPushButton("-&Cancel") { dlgReject(); exit (0);}
   };
}

if (library) {
   char bkslash = '/';
   int pos = strrchr(argv[0], bkslash);
   if (pos >= 0) {
      ulp_path = strsub(argv[0], 0, pos + 1);
   }
   int n = 0;
   library(L) {
   int posb = strrchr(argv[0], bkslash);
   if (posb >= 0) {
      ulp_path = strsub(argv[0], 0, posb + 1);
   }

   menue();

   script_change = filesetext(L.name, "~~~.scr");

   output(script_change, "wtD") {
      printf("DISPLAY NONE 91 92 93 94 95 96 97;\n");
      int firstf = 1;
      L.symbols(S) {
         printf("EDIT %s.SYM;\n", S.name);
         if (firstf) {
           printf("%s",grid);
           firstf = 0;
         }

         DoPackage(S);
      }

      printf("GRID DEFAULT;\n");
      printf("DISPLAY NONE 91 92 93 94 95 96 97;\n");
   }
   }
  exit ("SCRIPT '" + script_change + "';\n");
} else {
   dlgMessageBox("\n*** Start this ULP in a Library ***\n");
   exit (0);
}
