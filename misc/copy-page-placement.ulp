//string copy_from = "USB1";
//string apply_to[]  = {"USB2", "USB3", "USB4", "USB5", "USB6", "USB7", "USB8", "USB9", "USB10"};
//string exclude[] = {"R1", "R2", "R3", "R4", "R5", "H1"};
//string include[] = {"*_N", "*_P", "*_EN", "*_FAULT", "*_STATUS", "ILIM", "CTL1", "CTL2", "CTL3", "GND", "+5V"};
//int offset_x = 20;

string copy_from = "HUB1";
string apply_to[]  = {"HUB2", "HUB3"};
string exclude[] = {"DUMMY"};
string include[] = {"+3.3V"};
int offset_x = 60;

int offset_y = 0;

string cmd = "";

string strreplace(string in, string replace, string with){
	int start = strstr(in, replace);

	if(start < 0){
		return in;
	} else {
		return strsub(in, 0, start) + with + strsub(in, start+strlen(replace));
	}
}


string getElementName(string name){
	string a[];
	int n = strsplit(a, name, ':'); 
	return a[1];
}

int checkName(string name){
	//Check if one of the connecting elements
	for(int i = 0; include[i] != ""; i++){
		if(name == include[i]){
			return 2;
		}
		if(strsub(include[i], 0, 1) == "*"){
			string post = strsub(include[i], 1); 
			if(name == (copy_from + post)){
				return 3;
			}		
		}
	}

	//Check if part is within one of the modules
	string a[];
	int n = strsplit(a, name, ':'); 
	if(n == 2 && a[0] == copy_from){
		//Check if it is in exclude list
		for(int i = 0; exclude[i] != ""; i++){
			if(exclude[i] == a[1]){
				return 0;
			}
		}
		return 1;
	} else {
		return 0;
	}
}

string getNewName(string fullName, string newModuleName){
	//Check if wire is within modules
	string wname = "";
	int check = checkName(fullName);

	if(check == 1){			//Normal just in module
		wname = newModuleName + ":" + getElementName(fullName);
	} else if(check == 2){	//Use previous name for global signals
		wname = fullName;
	} else if(check == 3){	//Use new name
		wname = strreplace(fullName, copy_from, newModuleName);
	}
	return wname;	
}




board(B) {

	B.elements(E) {
		if(checkName(E.name)){			

			for(int i = 0; apply_to[i] != ""; i++){
				int mx = E.x + ((i+1) * mm2u(offset_x));
				int my = E.y + ((i+1) * mm2u(offset_y));
				string name = getNewName(E.name, apply_to[i]);

				sprintf(cmd, "%s MOVE %s (%f %f);\n", cmd, name, u2mm(mx), u2mm(my));
				string mirror = "";
				if(E.mirror){mirror = "M";}
				sprintf(cmd, "%s ROTATE =%sR%f %s;\n", cmd, mirror, E.angle, name);
			}
		}
	}
	sprintf(cmd, "%s SET WIRE_BEND 2;\n", cmd);


	B.signals(S){
		if(checkName(S.name)){	
			string name = getElementName(S.name);

			for(int i = 0; apply_to[i] != ""; i++){
				string newname = getNewName(S.name, apply_to[i]);
				
				S.wires(W){
					W.pieces(E){
						if(E.layer != 19){	//If no airwire
							int x1 = E.x1 + ((i+1) * mm2u(offset_x));
							int y1 = E.y1 + ((i+1) * mm2u(offset_y));
							int x2 = E.x2 + ((i+1) * mm2u(offset_x));
							int y2 = E.y2 + ((i+1) * mm2u(offset_y));

							sprintf(cmd, "%s LAYER %d;\n", cmd, E.layer);
							sprintf(cmd, "%s WIRE '%s' %f (%f %f) (%f %f);\n", 
								cmd, newname, 
								u2mm(E.width), 
								u2mm(x1), u2mm(y1),					
								u2mm(x2), u2mm(y2)
							);	
						}					
					}			
				}
				S.vias(E){
					string newname = getNewName(S.name, apply_to[i]);
					int x = E.x + ((i+1) * mm2u(offset_x));
					int y = E.y + ((i+1) * mm2u(offset_y));

					string shape = "round";
					if(E.shape[LAYER_TOP] == VIA_SHAPE_SQUARE){
						shape = "square";
					} else if (E.shape[LAYER_TOP] == VIA_SHAPE_OCTAGON) {
						shape = "octagon";
					}

					sprintf(cmd, "%s CHANGE DRILL %f;\n", cmd, u2mm(E.drill));
					sprintf(cmd, "%s VIA '%s' %f %s %d-%d (%f %f);\n", 
						cmd, newname, u2mm(E.diameter[LAYER_TOP]), 
						shape, E.start, E.end,  
						u2mm(x), u2mm(y)
					);
				}
				S.polygons(E){
					string newname = getNewName(S.name, apply_to[i]);

					string pour = "Solid";
					if(E.pour == POLYGON_POUR_HATCH){
						pour = "Hatch";
					} else if (E.pour == POLYGON_POUR_CUTOUT) {
						pour = "Cutout";
					}
					string thermals = "On";
					if(E.thermals == 0){
						thermals = "Off";
					} 
					string orphans = "On";
					if(E.orphans == 0){
						orphans = "Off";
					} 

					sprintf(cmd, "%s LAYER %d;\n", cmd, E.layer);
					sprintf(cmd, "%s CHANGE POUR %s;\n", cmd, pour);
					sprintf(cmd, "%s CHANGE THERMALS %s;\n", cmd, thermals);
					sprintf(cmd, "%s CHANGE ORPHANS %s;\n", cmd, orphans);
					sprintf(cmd, "%s CHANGE RANK %d;\n", cmd, E.rank);					
					sprintf(cmd, "%s CHANGE SPACING %f;\n", cmd, u2mm(E.spacing));
					sprintf(cmd, "%s CHANGE ISOLATE %f;\n", cmd, u2mm(E.isolate));

					sprintf(cmd, "%s POLYGON '%s' %f ", 
						cmd, newname, u2mm(E.width)
					);


					int ran = 0;
					int x1 = -1;
					int y1 = -1;


					E.wires(W){
						if(!ran){
							x1 = W.x1 + ((i+1) * mm2u(offset_x));
							y1 = W.y1 + ((i+1) * mm2u(offset_y));

							sprintf(cmd, "%s (%f %f)", cmd, 
								u2mm(x1), u2mm(y1)
							);		

							ran = 1;
						}


						int x2 = W.x2 + ((i+1) * mm2u(offset_x));
						int y2 = W.y2 + ((i+1) * mm2u(offset_y));

						sprintf(cmd, "%s (%f %f)", cmd, 				
							u2mm(x2), u2mm(y2)
						);						
					}
					if(ran){
						sprintf(cmd, "%s (%f %f)", cmd, 
							u2mm(x1), u2mm(y1)
						);	
					}


					sprintf(cmd, "%s;\n", cmd);
				}
			}
		}
	}


}

exit(cmd);
