if(EAGLE_VERSION < 5 || (EAGLE_VERSION == 5 && EAGLE_RELEASE < 10))
{
	dlgMessageBox("This ULP requires EAGLE 5.10 or higher to work");
}

string download_ulp_dir = "";

int downloadStringEndsWith(string haystack, string needle)
{
	string last = strsub(haystack, strlen(haystack) - strlen(needle));
	return (last == needle);
}

string downloadResverseSearch(string path, string needle)
{
	string a[], dirs[];
	int dir_count;

	dirs[dir_count++] = path;

	for(int k = 0; k < dir_count; k++)
	{
		int n = fileglob(a, dirs[k] + "*");
		for(int i = 0; i < n; i++)
		{
			if(downloadStringEndsWith(a[i], "/"))
			{
				dirs[dir_count++] = a[i];		
			}
			if(downloadStringEndsWith(a[i], needle))
			{
				return a[i];
			}
		}
	}
	return "";
}

string downloadGetUlpDir(string outp)
{
	return download_ulp_dir + outp;	
}

void downloadInit()
{
	for(int k = 0; path_ulp[k] != ""; k++)
	{
		string tmp = downloadResverseSearch(path_ulp[k], "Include_Download.ulp");
		if(tmp != "")
		{
			download_ulp_dir = filedir(tmp);
		}
	}
}

void download(string url, string outp, string parameter)
{
	output(outp)
	{
		string result;
		netpost(result, url, parameter);
		printf("%s",result);
	}
}

string downloadEscapeString(string data)
{
	string dout;
	for(int i = 0; i < strlen(data); i++)
	{
		sprintf(dout, "%s%%%02x", dout, data[i]);
	}
	return dout;
}


downloadInit();
