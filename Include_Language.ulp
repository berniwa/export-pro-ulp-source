#include "Include_String.ulp"

string  lanContent = "";
int 	lanLines = 0;
string  lan="";

void lanLoadText(string languageFile)
{
	if (languageFile=="") {
		languageFile="lang_English.txt";
	}

	lan=getUlpDir(languageFile);
	lanLines = fileread(lanContent, lan);
}

/* Parameters look like: grid 5 mm, outline 5 x 5 mm */
string lanWord(string parameter, string haystack)
{
	string data = "";

	parameter = parameter + " =";

	int start = strstr(haystack, parameter, 0);
	int len = strlen(parameter) + 1;
	int end = 0;

	if(start != -1)
	{
		end = strstr(haystack, "\n", start);
		end = end==-1?strlen(haystack):end;

		data = strsub(haystack, start + len , end-(start+len));
	}

	return stringTrim(data);
}

string lanGetText(string name)
{
	string result = "";
	for(int i = 0; i < lanLines; i++)
	{
		result = lanWord(name, lanContent);
		if(result != "")
		{
			return result;
		}
	}

	return name+" was not found in language.txt";
}
