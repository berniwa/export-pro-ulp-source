string execute = "";

int rerun = 1, save = 1;

string list[], names[], values[], packages[], distributor[], manufacturer[], order_no[], part_no[];
int count,  pages[];

void updateAttributes()
{
	count = 0;
	schematic(SCH)
	{
		SCH.sheets(S)
		{	
			S.parts(P)
			{
				if(P.device.package)
				{
					names[count] 		= P.name;
					values[count]		= P.value;
					packages[count]		= P.device.package.name;
					pages[count]		= S.number;
					distributor[count]	= P.attribute["DISTRIBUTOR"];
					order_no[count]		= P.attribute["ORDER_NO"];
					manufacturer[count]	= P.attribute["MANUFACTURER"];
					part_no[count]		= P.attribute["PART_NO"];
	
					count++;
				}						
			}			
		}
	}	
}

void updateAttributeList()
{
	for(int i = 0; i < count; i++)
	{
		sprintf(list[i], "%s\t%s\t%s\t%d\t%s\t%s\t%s\t%s\t", 
			names[i], values[i], packages[i] , pages[i], 
			distributor[i], order_no[i], 
			manufacturer[i], part_no[i]
		);	
	}
}


void findAndChange(int selected, int mode)
{
	int found = 0;

	for(int i = 0; i < count; i++)
	{
		if(	(mode == 0 && names[i] == names[selected]) || 
			(mode == 1 && values[i] == values[selected] && packages[i] == packages[selected]) || 
			(mode == 2 && values[i] == values[selected]) 
		)
		{
			sprintf(execute, "%s EDIT .s%d;\n",  execute, pages[i]);
			sprintf(execute, "%s ATTRIBUTE %s MANUFACTURER \'%s\';\n", 	execute, names[i], manufacturer[selected]);
			sprintf(execute, "%s ATTRIBUTE %s PART_NO \'%s\';\n", 	execute, names[i], part_no[selected]);
			sprintf(execute, "%s ATTRIBUTE %s DISTRIBUTOR \'%s\';\n", 	execute, names[i], distributor[selected]);
			sprintf(execute, "%s ATTRIBUTE %s ORDER_NO \'%s\';\n", 	execute, names[i], order_no[selected]);
			found = 1;

			manufacturer[i] 	= manufacturer[selected];
			part_no[i]	= part_no[selected];
			distributor[i] 	= distributor[selected];
			order_no[i] 	= order_no[selected];
		}	

	}
	if(!found){dlgMessageBox("Device with value " + values[selected] + " not found!");}
}




void editDevice(int selected)
{
	int saveDevice = 1;
	int mode = 1;

	dlgDialog("Set Attributes for Device")
	{
		dlgGroup("Update Mode")
		{
			dlgHBoxLayout
			{
 				dlgRadioButton("Part Name", mode);
  				dlgRadioButton("Device Value && Package", mode);
  				dlgRadioButton("Device Value", mode);
			}			
		}

		dlgGroup("Device Information")
		{
			dlgHBoxLayout
			{
				dlgLabel("Part");
				dlgLabel(names[selected]);	
				dlgLabel("Value");
				dlgLabel(values[selected]);
				dlgLabel("Package");	
				dlgLabel(packages[selected]);
			}
			/*
			dlgHBoxLayout
			{
				string s = "";
				sprintf(s, "<html><a href=\"at.farnell.com/%s\">at.farnell.com/%s</a></html>", order_no[selected], order_no[selected]);
				dlgLabel(s); 
			}
			*/
		}
		dlgGroup("New Values")
		{		
			dlgGridLayout
			{
				dlgCell(0, 0) dlgLabel("DISTRIBUTOR");
				dlgCell(0, 1) dlgStringEdit(distributor[selected]);
				dlgCell(0, 2) dlgLabel("ORDER_NO");
				dlgCell(0, 3) dlgStringEdit(order_no[selected]);	
				dlgCell(1, 0) dlgLabel("MANUFACTURER");
				dlgCell(1, 1) dlgStringEdit(manufacturer[selected]);	
				dlgCell(1, 2) dlgLabel("PART_NO");
				dlgCell(1, 3) dlgStringEdit(part_no[selected]);	
			}
		}
		dlgHBoxLayout
		{
			dlgPushButton("Abbrechen"){saveDevice = 0; dlgReject(); }
			dlgPushButton("Speichern"){dlgAccept(); }
		}
	};
	if(saveDevice)
	{
		findAndChange(selected, mode);
	}	
}


int showListOfDevices()
{
	
	int count = 0; 
	int selected = 0;

	updateAttributes();

	while(1)
	{
		updateAttributeList();
	
		dlgDialog("Set Attributes for Device with value")
		{
			dlgListView("Part\tValue\tPackage\tSheet\tDistributor\tOrder No.\tManufacturer\tPart No.", list, selected)
			{
				editDevice(selected);
				dlgAccept();
			}
			dlgHBoxLayout
			{
				dlgPushButton("Abbrechen"){dlgReject(); return 0;}
				dlgPushButton("Speichern"){dlgAccept(); return 1;}
			}
		};
	}

	return 0;
}

if(showListOfDevices())
{
	exit(execute);	
}
