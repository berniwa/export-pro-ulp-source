/************************************************************/
/* HTLExportPro_Sat.ulp                                     */
/* - Generiert Solid Edge kompatible .sat Files             */
/************************************************************/
/* (c) Copyright 2011, Bernhard Wörndl-Aichriedler          */
/* E-Mail: bwa@berniwa.com                                  */
/* Homepage: www.berniwa.com                                */
/************************************************************/
/* Original von Ed Slatt                                    */
/* Geändert 2007 bei Norbert Winter                         */
/* Geändert bei Andreas Wallinger                           */
/************************************************************/
/* Letzte Änderung am 18.02.2011                            */
/* Version 1                                                */
/************************************************************/


#usage "ACIS-SAT Generator\n\n"
       "ACIS-SAT exportiert ein ACIS model von der Printplatte als\n"
       "Standard ACIS Text (SAT) - (Einheit: mm).  Das ACIS model beinhaltet die\n"
       "Printplatte (rectangular slab) mit Bohrungen!  Diese Datei kann in\n"
       "ein CAD Programm importiert werden - vector-based\n"
       "Sie koennen auch an der Position des Origins jedes Bauteils eine\n"
       "kleine Bohrung plazieren lassen um leichter SMD-Bauteile\n"
       "bestuecken zu koennen\n"
       "Folgende Programme unterstüzen das SAT - Format:\n"
       "Solid Edge(!), Inventor, CADKEY, CoCreate Designer, Cosmos, Form/Z, Microstation,\n"
       "AutoCAD, SolidWorks, IronCAD and more.\n\n"
       "ACIS\n"
       "ACIS is a new generation, vector-based, three-dimensional,\n"
       "boundary representation, and geometric modeler from Spatial\n"
       "Technology Inc.  The ACIS Geometric Modeler consists of the ACIS\n"
       "Kernel, the core solid modeler, and ACIS Parametric Surfaces, that\n"
       "extends the kernel to handle sculptured surfaces.\n"
       "The ACIS Kernel provides functionality common to many applications\n"
       "combined with flexible means to adapt and extend the modeler to\n"
       "particular requirements.  It is compact, efficient, and reliable\n"
       "and can be embedded in a wide range of mechanical engineering\n"
       "applications, from creative design to analysis and manufacture.\n"
       "\nAutor:  Norbert Winter (original: Ed Slatt)\n"
       "Editiert: Andreas Wallinger"



// THIS PROGRAM IS PROVIDED AS IS AND WITHOUT WARRANTY OF ANY KIND, EXPRESSED OR IMPLIED
//
//
int mit_origins=0;
int cur_index=-1;
int last_top_loop[]; // 0 - index, 1 - next_loop, 2 - coedge, 3 - face
int last_bot_loop[];
int last_face[];     // 0 - index, 1 - feature, 2 - next_face, 3 - loop, 4 - shell, 5 - surface, 6 - direction (0 - forward single | 1 - reversed single)
string file_content="";

int get_next_index()
{
  cur_index++;
  return cur_index;
}

void start_body()
{
  string bc;

  sprintf(bc, "-0 body \$-1 \$1 \$-1 \$-1 #\n"); file_content+=bc;
  sprintf(bc, "-1 lump \$-1 \$-1 \$2 \$0 #\n"); file_content+=bc;
  sprintf(bc, "-2 shell \$-1 \$-1 \$-1 \$5 \$1 #\n"); file_content+=bc;

  cur_index=2;
}

void finish_acis()
{
  string header;
  sprintf(header, "105 %d 1 0\n", cur_index+1);

 // last face
  string last_face_string;
  sprintf(last_face_string, "-%d face \$%d \$%d \$%d \$%d \$-1 \$%d reversed single #\n",
    last_face[0], last_face[1], last_face[2], last_face[3], last_face[4], last_face[5]);

 // last top loop
  string last_top_loop_string;
  sprintf(last_top_loop_string, "-%d loop \$-1 \$%d \$%d \$%d #\n",
    last_top_loop[0], last_top_loop[1], last_top_loop[2], last_top_loop[3]);

 // last bot loop
  string last_bot_loop_string;
  sprintf(last_bot_loop_string, "-%d loop \$-1 \$%d \$%d \$%d #\n",
    last_bot_loop[0], last_bot_loop[1], last_bot_loop[2], last_bot_loop[3]);

  string last_line_string;
  sprintf(last_line_string, "-%d\n", cur_index+1);

  file_content = header + file_content + last_face_string + last_top_loop_string + last_bot_loop_string + last_line_string;
}

void slab(real x1, real x2, real y1, real y2, real z1, real z2)
{
 // hardwires pointers to keep this trivial application simple

  string sc;

  sprintf(sc, "-17 plane-surface \$-1   0   0 %f  0  0  1 1 0  0 0 #\n", z1); file_content+=sc;
  sprintf(sc, "-11 plane-surface \$-1   0   0 %f  0  0  1 1 0  0 0 #\n", z2); file_content+=sc;
  sprintf(sc, "-25 plane-surface \$-1   0 %f   0  0  1  0 0 0  1 0 #\n", y1); file_content+=sc;
  sprintf(sc, "-48 plane-surface \$-1   0 %f   0  0 -1  0 0 0 -1 0 #\n", y2); file_content+=sc;
  sprintf(sc, "-35 plane-surface \$-1 %f   0   0  1  0  0 0 0 -1 0 #\n", x1); file_content+=sc;
  sprintf(sc, "-70 plane-surface \$-1 %f   0   0 -1  0  0 0 0  1 0 #\n", x2); file_content+=sc;
  sprintf(sc, "-5 face \$8 \$9 \$18 \$2 \$-1 \$11 forward single #\n"); file_content+=sc;
  sprintf(sc, "-9 face \$14 \$15 \$26 \$2 \$-1 \$17 reversed single #\n"); file_content+=sc;
  sprintf(sc, "-15 face \$22 \$23 \$24 \$2 \$-1 \$25 reversed single #\n"); file_content+=sc;
  sprintf(sc, "-33 face \$45 \$46 \$47 \$2 \$-1 \$48 reversed single #\n"); file_content+=sc;
  sprintf(sc, "-23 face \$32 \$33 \$34 \$2 \$-1 \$35 reversed single #\n"); file_content+=sc;
  sprintf(sc, "-8 feature-ospam-attrib \$-1 \$-1 \$-1 \$5 0 #\n"); file_content+=sc;
  sprintf(sc, "-14 feature-ospam-attrib \$-1 \$-1 \$-1 \$9 0 #\n"); file_content+=sc;
  sprintf(sc, "-22 feature-ospam-attrib \$-1 \$-1 \$-1 \$15 0 #\n"); file_content+=sc;
  sprintf(sc, "-45 feature-ospam-attrib \$-1 \$-1 \$-1 \$33 0 #\n"); file_content+=sc;
  sprintf(sc, "-32 feature-ospam-attrib \$-1 \$-1 \$-1 \$23 0 #\n"); file_content+=sc;
  sprintf(sc, "-69 feature-ospam-attrib \$-1 \$-1 \$-1 \$46 0 #\n"); file_content+=sc;
  sprintf(sc, "-94 point  \$-1 %f %f %f #\n", x2, y2, z2); file_content+=sc;
  sprintf(sc, "-105 point \$-1 %f %f %f #\n", x1, y2, z2); file_content+=sc;
  sprintf(sc, "-109 point \$-1 %f %f %f #\n", x1, y2, z1); file_content+=sc;
  sprintf(sc, "-93 point  \$-1 %f %f %f #\n", x2, y1, z2); file_content+=sc;
  sprintf(sc, "-99 point  \$-1 %f %f %f #\n", x1, y1, z2); file_content+=sc;
  sprintf(sc, "-102 point \$-1 %f %f %f #\n", x2, y2, z1); file_content+=sc;
  sprintf(sc, "-103 point \$-1 %f %f %f #\n", x2, y1, z1); file_content+=sc;
  sprintf(sc, "-100 point \$-1 %f %f %f #\n", x1, y1, z1); file_content+=sc;
  sprintf(sc, "-66 vertex \$-1 \$41 \$94 #\n"); file_content+=sc;
  sprintf(sc, "-88 vertex \$-1 \$60 \$105 #\n"); file_content+=sc;
  sprintf(sc, "-96 vertex \$-1 \$83 \$109 #\n"); file_content+=sc;
  sprintf(sc, "-65 vertex \$-1 \$41 \$93 #\n"); file_content+=sc;
  sprintf(sc, "-78 vertex \$-1 \$87 \$99 #\n"); file_content+=sc;
  sprintf(sc, "-84 vertex \$-1 \$57 \$102 #\n"); file_content+=sc;
  sprintf(sc, "-85 vertex \$-1 \$91 \$103 #\n"); file_content+=sc;
  sprintf(sc, "-79 vertex \$-1 \$95 \$100 #\n"); file_content+=sc;
  sprintf(sc, "-90 straight-curve  \$-1 %f %f %f  1  0  0 #\n", x1, y1, z2); file_content+=sc;
  sprintf(sc, "-101 straight-curve \$-1 %f %f %f  1  0  0 #\n", x1, y2, z1); file_content+=sc;
  sprintf(sc, "-89 straight-curve  \$-1 %f %f %f -1  0  0 #\n", x1, y2, z2); file_content+=sc;
  sprintf(sc, "-98 straight-curve  \$-1 %f %f %f -1  0  0 #\n", x1, y1, z1); file_content+=sc;
  sprintf(sc, "-67 straight-curve  \$-1 %f %f %f  0  1  0 #\n", x2, y1, z2); file_content+=sc;
  sprintf(sc, "-108 straight-curve \$-1 %f %f %f  0  1  0 #\n", x1, y1, z1); file_content+=sc;
  sprintf(sc, "-104 straight-curve \$-1 %f %f %f  0 -1  0 #\n", x1, y1, z2); file_content+=sc;
  sprintf(sc, "-86 straight-curve  \$-1 %f %f %f  0 -1  0 #\n", x2, y1, z1); file_content+=sc;
  sprintf(sc, "-107 straight-curve \$-1 %f %f %f  0  0 -1 #\n", x2, y2, z1); file_content+=sc;
  sprintf(sc, "-97 straight-curve  \$-1 %f %f %f  0  0 -1 #\n", x1, y2, z1); file_content+=sc;
  sprintf(sc, "-106 straight-curve \$-1 %f %f %f  0  0 -1 #\n", x2, y1, z1); file_content+=sc;
  sprintf(sc, "-80 straight-curve  \$-1 %f %f %f  0  0 -1 #\n", x1, y1, z1); file_content+=sc;
  sprintf(sc, "-61 edge \$-1 \$78 \$65 \$51 \$90 0 #\n"); file_content+=sc;
  sprintf(sc, "-83 edge \$-1 \$96 \$84 \$82 \$101 0 #\n"); file_content+=sc;
  sprintf(sc, "-60 edge \$-1 \$66 \$88 \$59 \$89 0 #\n"); file_content+=sc;
  sprintf(sc, "-77 edge \$-1 \$85 \$79 \$50 \$98 0 #\n"); file_content+=sc;
  sprintf(sc, "-41 edge \$-1 \$65 \$66 \$40 \$67 0 #\n"); file_content+=sc;
  sprintf(sc, "-95 edge \$-1 \$79 \$96 \$72 \$108 0 #\n"); file_content+=sc;
  sprintf(sc, "-87 edge \$-1 \$88 \$78 \$73 \$104 0 #\n"); file_content+=sc;
  sprintf(sc, "-57 edge \$-1 \$84 \$85 \$56 \$86 0 #\n"); file_content+=sc;
  sprintf(sc, "-92 edge \$-1 \$66 \$84 \$63 \$107 0 #\n"); file_content+=sc;
  sprintf(sc, "-75 edge \$-1 \$88 \$96 \$74 \$97 0 #\n"); file_content+=sc;
  sprintf(sc, "-91 edge \$-1 \$65 \$85 \$62 \$106 0 #\n"); file_content+=sc;
  sprintf(sc, "-53 edge \$-1 \$78 \$79 \$52 \$80 0 #\n"); file_content+=sc;
  sprintf(sc, "-39 coedge \$-1 \$28 \$58 \$51 \$61 0 \$18 \$-1 #\n"); file_content+=sc;
  sprintf(sc, "-58 coedge \$-1 \$39 \$38 \$73 \$87 0 \$18 \$-1 #\n"); file_content+=sc;
  sprintf(sc, "-38 coedge \$-1 \$58 \$28 \$59 \$60 0 \$18 \$-1 #\n"); file_content+=sc;
  sprintf(sc, "-28 coedge \$-1 \$38 \$39 \$40 \$41 0 \$18 \$-1 #\n"); file_content+=sc;
  sprintf(sc, "-51 coedge \$-1 \$36 \$76 \$39 \$61 1 \$24 \$-1 #\n"); file_content+=sc;
  sprintf(sc, "-76 coedge \$-1 \$51 \$50 \$62 \$91 1 \$24 \$-1 #\n"); file_content+=sc;
  sprintf(sc, "-50 coedge \$-1 \$76 \$36 \$54 \$77 1 \$24 \$-1 #\n"); file_content+=sc;
  sprintf(sc, "-36 coedge \$-1 \$50 \$51 \$52 \$53 0 \$24 \$-1 #\n"); file_content+=sc;
  sprintf(sc, "-55 coedge \$-1 \$37 \$81 \$82 \$83 0 \$26 \$-1 #\n"); file_content+=sc;
  sprintf(sc, "-81 coedge \$-1 \$55 \$54 \$72 \$95 0 \$26 \$-1 #\n"); file_content+=sc;
  sprintf(sc, "-54 coedge \$-1 \$81 \$37 \$50 \$77 0 \$26 \$-1 #\n"); file_content+=sc;
  sprintf(sc, "-37 coedge \$-1 \$54 \$55 \$56 \$57 0 \$26 \$-1 #\n"); file_content+=sc;
  sprintf(sc, "-63 coedge \$-1 \$40 \$56 \$71 \$92 1 \$64 \$-1 #\n"); file_content+=sc;
  sprintf(sc, "-56 coedge \$-1 \$63 \$62 \$37 \$57 1 \$64 \$-1 #\n"); file_content+=sc;
  sprintf(sc, "-62 coedge \$-1 \$56 \$40 \$76 \$91 0 \$64 \$-1 #\n"); file_content+=sc;
  sprintf(sc, "-40 coedge \$-1 \$62 \$63 \$28 \$41 1 \$64 \$-1 #\n"); file_content+=sc;
  sprintf(sc, "-73 coedge \$-1 \$49 \$52 \$58 \$87 1 \$34 \$-1 #\n"); file_content+=sc;
  sprintf(sc, "-52 coedge \$-1 \$73 \$72 \$36 \$53 1 \$34 \$-1 #\n"); file_content+=sc;
  sprintf(sc, "-72 coedge \$-1 \$52 \$49 \$81 \$95 1 \$34 \$-1 #\n"); file_content+=sc;
  sprintf(sc, "-49 coedge \$-1 \$72 \$73 \$74 \$75 0 \$34 \$-1 #\n"); file_content+=sc;
  sprintf(sc, "-74 coedge \$-1 \$59 \$82 \$49 \$75 1 \$47 \$-1 #\n"); file_content+=sc;
  sprintf(sc, "-82 coedge \$-1 \$74 \$71 \$55 \$83 1 \$47 \$-1 #\n"); file_content+=sc;
  sprintf(sc, "-71 coedge \$-1 \$82 \$59 \$63 \$92 0 \$47 \$-1 #\n"); file_content+=sc;
  sprintf(sc, "-59 coedge \$-1 \$71 \$74 \$38 \$60 1 \$47 \$-1 #\n"); file_content+=sc;
  sprintf(sc, "-24 loop \$-1 \$-1 \$36 \$15 #\n"); file_content+=sc;
  sprintf(sc, "-34 loop \$-1 \$-1 \$49 \$23 #\n"); file_content+=sc;
  sprintf(sc, "-64 loop \$-1 \$-1 \$62 \$46 #\n"); file_content+=sc;
  sprintf(sc, "-47 loop \$-1 \$-1 \$71 \$33 #\n"); file_content+=sc;

 // -46 face \$69 \$-1 \$64 \$2 \$-1 \$70 reversed single #
  last_face[0] = 46;
  last_face[1] = 69;
  last_face[2] = -1;
  last_face[3] = 64;
  last_face[4] = 2;
  last_face[5] = 70;
  last_face[6] = 1;

 // -18 loop \$-1 \$-1 \$28 \$5 #
  last_top_loop[0] = 18;
  last_top_loop[1] = -1;
  last_top_loop[2] = 28;
  last_top_loop[3] = 5;

 // -26 loop \$-1 \$-1 \$37 \$9 #
  last_bot_loop[0] = 26;
  last_bot_loop[1] = -1;
  last_bot_loop[2] = 37;
  last_bot_loop[3] = 9;

  cur_index=109;
}

void include_hole(real x_loc, real y_loc, real radius, real z1, real z2)
{
  int cone_index = get_next_index();
  int face_index = get_next_index();
  int next_face_index = last_face[2];
  last_face[2] = face_index;
 
  int feature_index = get_next_index();

  int ellipse_top_index = get_next_index();
  int edge_top_index = get_next_index();
  int coedge_top_index = get_next_index();

  int ellipse_bot_index = get_next_index();
  int edge_bot_index = get_next_index();
  int coedge_bot_index = get_next_index();

  int coedge0_index = get_next_index();
  int coedge1_index = get_next_index();

  int point_top_index = get_next_index();
  int vertex_top_index = get_next_index();

  int point_bot_index = get_next_index();
  int vertex_bot_index = get_next_index();

  int loop0_index = get_next_index();
  int loop1_index = get_next_index();

  int loop_top_index = get_next_index();
  int next_loop_top_index = last_top_loop[1];
  last_top_loop[1] = loop_top_index;

  int loop_bot_index = get_next_index();
  int next_loop_bot_index = last_bot_loop[1];
  last_bot_loop[1] = loop_bot_index;

  real x_plus_radius = x_loc + radius;

 // bottom edge is hooked up with 1s
 // top is hooked up with 0s

  string hc;

  sprintf(hc, "-%d cone-surface \$-1 %f %f %f 0 0 -1 %f 0 0 1 0 1 0 #\n", cone_index, x_loc, y_loc, z1, radius); file_content+=hc;
  sprintf(hc, "-%d face \$%d \$%d \$%d \$2 \$-1 \$%d reversed single #\n", face_index, feature_index, next_face_index, loop0_index, cone_index); file_content+=hc;
  sprintf(hc, "-%d feature-ospam-attrib \$-1 \$-1 \$-1 \$%d 1 #\n", feature_index, face_index); file_content+=hc;
  sprintf(hc, "-%d ellipse-curve \$-1 %f %f %f 0 0  1 %f 0 0 1 #\n", ellipse_bot_index, x_loc, y_loc, z1, radius); file_content+=hc;
  sprintf(hc, "-%d ellipse-curve \$-1 %f %f %f 0 0 -1 %f 0 0 1 #\n", ellipse_top_index, x_loc, y_loc, z2, radius); file_content+=hc;
  sprintf(hc, "-%d edge \$-1 \$%d \$%d \$%d \$%d 0 #\n", edge_bot_index, vertex_bot_index, vertex_bot_index, coedge1_index, ellipse_bot_index); file_content+=hc;
  sprintf(hc, "-%d edge \$-1 \$%d \$%d \$%d \$%d 0 #\n", edge_top_index, vertex_top_index, vertex_top_index, coedge0_index, ellipse_top_index); file_content+=hc;
  sprintf(hc, "-%d point \$-1 %f %f %f #\n", point_top_index, x_plus_radius, y_loc, z2); file_content+=hc;
  sprintf(hc, "-%d point \$-1 %f %f %f #\n", point_bot_index, x_plus_radius, y_loc, z1); file_content+=hc;
  sprintf(hc, "-%d vertex \$-1 \$%d \$%d #\n", vertex_top_index, edge_top_index, point_top_index); file_content+=hc;
  sprintf(hc, "-%d vertex \$-1 \$%d \$%d #\n", vertex_bot_index, edge_bot_index, point_bot_index); file_content+=hc;
  sprintf(hc, "-%d coedge \$-1 \$%d \$%d \$%d \$%d 0 \$%d \$-1 #\n", coedge_top_index, coedge_top_index, coedge_top_index, coedge0_index, edge_top_index, loop_top_index); file_content+=hc;
  sprintf(hc, "-%d coedge \$-1 \$%d \$%d \$%d \$%d 0 \$%d \$-1 #\n", coedge_bot_index, coedge_bot_index, coedge_bot_index, coedge1_index, edge_bot_index, loop_bot_index); file_content+=hc;
  sprintf(hc, "-%d loop \$-1 \$%d \$%d \$5 #\n", loop_top_index, next_loop_top_index, coedge_top_index); file_content+=hc;
  sprintf(hc, "-%d loop \$-1 \$%d \$%d \$9 #\n", loop_bot_index, next_loop_bot_index, coedge_bot_index); file_content+=hc;
  sprintf(hc, "-%d coedge \$-1 \$%d \$%d \$%d \$%d 1 \$%d \$-1 #\n", coedge0_index, coedge0_index, coedge0_index, coedge_top_index, edge_top_index, loop0_index); file_content+=hc;
  sprintf(hc, "-%d coedge \$-1 \$%d \$%d \$%d \$%d 1 \$%d \$-1 #\n", coedge1_index, coedge1_index, coedge1_index, coedge_bot_index, edge_bot_index, loop1_index); file_content+=hc;
  sprintf(hc, "-%d loop \$-1 \$%d \$%d \$%d #\n", loop0_index, loop1_index, coedge0_index, face_index); file_content+=hc;
  sprintf(hc, "-%d loop \$-1 \$-1 \$%d \$%d #\n", loop1_index, coedge1_index, face_index); file_content+=hc;
}

void u_hole(int x, int y, int drill)
{
  string hole_entry;
  sprintf(hole_entry, "hole %d %d %d\n", x, y, drill);

  real x_loc, y_loc, radius, z1, z2;
  x_loc = u2mm(x);
  y_loc = u2mm(y);
  radius = u2mm(drill)/2;
  z1 = 0;
  z2 = 0;

  include_hole(x_loc, y_loc, radius, z1, z2);
}

if (board) board(B)
{
  string board_dimensions;

  start_body();
  real x1, x2, y1, y2, z1, z2;
  x1 = u2mm(B.area.x1);  x2 = u2mm(B.area.x2);  y1 = u2mm(B.area.y1);  y2 = u2mm(B.area.y2);  z1 = 0;  z2 = 1.6;
  slab(x1, x2, y1, y2, z1, z2);

  B.holes(L)
  {
    u_hole(L.x, L.y, L.drill);
  }
  B.elements(E)
  {
    E.package.holes(H)
    {
      u_hole(H.x, H.y, H.drill);
    }
    E.package.contacts(C)
    {
      if (C.pad) 
      {
        u_hole(C.pad.x, C.pad.y, C.pad.drill);
      }
    }
  }	
  B.signals(S)
  {
    S.vias(V)
    {
      u_hole(V.x, V.y, V.drill);
    }
  }
  if(mit_origins){
      B.elements(E) //Origins aller elemente
      {
    	u_hole(E.x, E.y, 511);
      }
  }
  finish_acis();

  string fileName = argv[1];
  if (fileName == "") exit(0);

  output(fileName)
  {
    printf("%s",file_content);
  }

  exit (0);
}
else 
{
	dlgMessageBox(":ACIS-SAT must be started from a board.", "OK");
	exit (1);
}
