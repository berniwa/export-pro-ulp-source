#include "Include_Misc.ulp";
#include "Include_Language.ulp";
#include "Include_String.ulp";

string 
cfg_textLanguage = "", 
cfg_userName = "", 
cfg_shortUserName = "",
cfg_pricingURL = "http://eagle.berniwa.com/price.php",
cfg_defaultTolerance = "1%",
cfg_defaultVoltage = "50V"
;

//variables for bom export presets
string 	cfg_bomPreNames[];
real 	cfg_bomPreOffX[];
real 	cfg_bomPreOffY[];
real 	cfg_bomPreWidth[];
int 	cfg_bomPreCount;

void saveConfig() {
	cfgset("ULP:ExportPro.language",cfg_textLanguage);
	cfgset("ULP:ExportPro.userName",cfg_userName);
	cfgset("ULP:ExportPro.shortUserName",cfg_shortUserName);
	cfgset("ULP:ExportPro.pricingURL",cfg_pricingURL);
	cfgset("ULP:ExportPro.defaultTolerance",cfg_defaultTolerance);
	cfgset("ULP:ExportPro.defaultVoltage",cfg_defaultVoltage);

	if(cfg_bomPreNames[1]!=""){
		string data="";
		int i=1;
		while(1){
			sprintf(data,"%s%s,%f,%f,%f", data, cfg_bomPreNames[i], cfg_bomPreOffX[i], cfg_bomPreOffY[i], cfg_bomPreWidth[i]);

			if(cfg_bomPreNames[++i]){
				data+=";";
			}
			else {
				break;
			}
		}
		cfgset("ULP:ExportPro.bomPresets",data);
	}
}

string isNotMenu(){
	string pathSCR="",scrI;
	string pathO="";

	for(int i=0;path_scr[i];i++){
		pathSCR = path_scr[i]+"/eagle.scr";
		
		if(filesize(pathSCR)){
			string scrI, scrO;

			fileread(scrI,pathSCR);

			if(strstr(scrI,"/ExportPro.ulp")==-1){
				pathO=pathSCR;
			}
			break;
		}
	}

	return pathO;
}

void setToMenu(){
	string pathULP = filedir(argv[0]);
	string pathSCR = isNotMenu();
	if(pathSCR){
		string scrO,scrI;

		fileread(scrI,pathSCR);

		scrO  = strsub(scrI,0,strstr(scrI,"MENU",strstr(scrI,"BRD:"))+5);
		scrO += "'Export Pro: RUN "+pathULP+"ExportPro.ulp;'\\\n\t";
		scrO += "'Select Part: RUN "+pathULP+"SelectPart.ulp;'\\\n\t";
		scrO += strsub(scrI,strstr(scrI,"MENU",strstr(scrI,"BRD:"))+5,(strstr(scrI,"MENU",strstr(scrI,"SCH:"))-strstr(scrI,"MENU",strstr(scrI,"BRD:"))));
		scrO += "'Export Pro: RUN "+pathULP+"ExportPro.ulp;'\\\n\t";
		scrO += "'Select Part: RUN "+pathULP+"SelectPart.ulp;'\\\n\t";
		scrO += strsub(scrI,strstr(scrI,"MENU",strstr(scrI,"SCH:"))+5);

		scrO = stringReplace(scrO,"SCH:","SCH:\nSET CONTEXT instance SelectPart 'run "+getUlpDir("../SelectPart.ulp")+" 1';");

		output(pathSCR){
			printf(scrO);
		}
	}	
}

char editUserConfig(){
	if (!filesize(getUlpDir("../Languages/"+cfg_textLanguage))) {
		cfg_textLanguage=language()+".txt";
		if (!filesize(getUlpDir("../Languages/"+cfg_textLanguage))) {
			cfg_textLanguage="en.txt";
		}
	}

	char update=0;
	string languages[];
	int languageCount = fileglob(languages,getUlpDir("../Languages/*.txt"));
	int n = 0;

	for(int i=0; i<languageCount; i++){
		languages[i] = filename(languages[i]);
		if(strstr(cfg_textLanguage,languages[i])!=-1){
			n=i;
		}
		languages[i] = strsub(languages[i],0,(strrstr(languages[i],".txt")));
	}

	cfg_textLanguage = languages[n]+".txt";
	string lastLanguage = cfg_textLanguage;
	lanLoadText(cfg_textLanguage);

	if(!cfg_userName){ //first start of the ulp
		int opt = dlgMessageBox(lanGetText("dlg.add2Menu"),lanGetText("general.yes"),lanGetText("general.no"));
		if (!opt){
			setToMenu();
		}
	}

	real tol = strtod(cfg_defaultTolerance);
	real volt = strtod(cfg_defaultVoltage);

	dlgDialog(lanGetText("settings.general")) {
		dlgVBoxLayout {
			dlgGroup(lanGetText("settings.general")) {
				dlgGridLayout {
					dlgCell(0, 0) dlgLabel(lanGetText("general.language")+":");
					dlgCell(0, 1) dlgComboBox(languages,n){
						cfg_textLanguage = languages[n]+".txt";
						update=1;
					};

					dlgCell(1, 0) dlgLabel(lanGetText("grneral.userName")+":");
					dlgCell(1, 1) dlgStringEdit(cfg_userName);
					dlgCell(2, 0) dlgLabel(lanGetText("general.shortName")+":");
					dlgCell(2, 1) dlgStringEdit(cfg_shortUserName);
					dlgCell(3, 0) dlgLabel(lanGetText("general.pricingURL")+":");
					dlgCell(3, 1) dlgStringEdit(cfg_pricingURL);
					dlgCell(4, 0) dlgLabel(lanGetText("settings.default.tolerance")+":");
					dlgCell(4, 1) dlgHBoxLayout {dlgRealEdit(tol); dlgLabel("%");}
					dlgCell(5, 0) dlgLabel(lanGetText("settings.default.voltage")+":");
					dlgCell(5, 1) dlgHBoxLayout {dlgRealEdit(volt); dlgLabel("V");}
				}
				if(isNotMenu()){
					dlgPushButton(lanGetText("settings.menu")){setToMenu();};
				}
			}

			dlgHBoxLayout{
			dlgPushButton(lanGetText("button.ok")){dlgAccept();};
				dlgPushButton(lanGetText("button.cancel")){
					update=0;
					cfg_textLanguage = lastLanguage;
					dlgReject();
				};
			}
		}
	};

	sprintf(cfg_defaultTolerance,"%g%%",tol);
	sprintf(cfg_defaultVoltage,"%gV",volt);

	saveConfig();
	return update;
}

void loadConfig(){
	
	cfg_textLanguage = cfgget("ULP:ExportPro.language",(language()+".txt"));
	cfg_userName = cfgget("ULP:ExportPro.userName");
	cfg_shortUserName = cfgget("ULP:ExportPro.shortUserName");
	cfg_pricingURL = cfgget("ULP:ExportPro.pricingURL",cfg_pricingURL);
	cfg_defaultTolerance = cfgget("ULP:ExportPro.defaultTolerance",cfg_defaultTolerance);
	cfg_defaultVoltage = cfgget("ULP:ExportPro.defaultVoltage",cfg_defaultVoltage);
	string tmp = cfgget("ULP:ExportPro.bomPresets");
	if(tmp!=""){
		string tmpa[];
		string tmpb[];
		cfg_bomPreCount = strsplit(tmpa,tmp,';');

		cfg_bomPreNames[0]="";

		for(int n=0; n<cfg_bomPreCount; n++){
			strsplit(tmpb,tmpa[n],',');

			cfg_bomPreNames[n+1]=tmpb[0];
			cfg_bomPreOffX[n+1]=strtod(tmpb[1]);
			cfg_bomPreOffY[n+1]=strtod(tmpb[2]);
			cfg_bomPreWidth[n+1]=strtod(tmpb[3]);
		}
	}
	if(cfg_userName=="") {
		editUserConfig();
	}
}
