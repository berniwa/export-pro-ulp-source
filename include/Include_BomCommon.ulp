/************************************************************/
/* Include_BomConfig.ulp                                    */
/* - Contains defines for proper BOM generator			    */
/************************************************************/
/* (c) Copyright 2016, Bernhard Wörndl-Aichriedler          */
/* xDevelop OG - Hardware Developer							*/
/* E-Mail: bwa@xdevelop.Autors            				    */
/* Homepage: www.xdevelop.at 								*/
/************************************************************/
/* Letzte Änderung am 15.02.2016                            */
/* Version 1.0 				                                */
/************************************************************/

string 	
	names[], 		values[], 		packages[], 
	distributor[], 	order_no[], 	manufacturer[], 
	part_no[],		price[], 		prices[], 		
	datasheet[],	min_qty[], 		qty_mul[],
	per_pkg[], 		available[], 	populate[], 
	note[], 		device[], 		description[];

int 	category[], pages[];

int partcount, partNr;

void bomLoadSchematic(UL_PART P, int s, string prefix){
	
	for(int i = 0;i<partcount;i++){		//to prevent parts to get listed multiple times
		if(names[i]==(prefix + P.name)){
			return;
		}
	}

	if(P.device.package) {
		names[partcount] 		= prefix + P.name;
		values[partcount]		= P.value;
		device[partcount]		= P.device.name;
		description[partcount] 	= P.device.package.description;
		packages[partcount]		= P.device.package.name;
		pages[partcount]		= s;
		distributor[partcount]	= P.attribute["DISTRIBUTOR"];
		order_no[partcount]		= P.attribute["ORDER_NO"];
		manufacturer[partcount]	= P.attribute["MANUFACTURER"];
		part_no[partcount]		= P.attribute["PART_NO"];
		price[partcount]		= P.attribute["PRICE"];
		prices[partcount]		= P.attribute["PRICES"];
		datasheet[partcount]	= P.attribute["DATASHEET"];
		min_qty[partcount]		= P.attribute["MINIMUM_QUANTITY"];
		qty_mul[partcount]		= P.attribute["QUANTITY_MULTIPLIER"];
		per_pkg[partcount]		= P.attribute["PARTS_PER_PACKAGE"];
		available[partcount]	= P.attribute["AVAILABLE_QUANTITY"];	
		populate[partcount]		= P.attribute["POPULATE"];
		note[partcount]			= P.attribute["NOTE"];
		if(P.attribute["CATEGORY"])
		{
			category[partcount]	= strtol(P.attribute["CATEGORY"]);
		}
		else
		{
			category[partcount] = bomCategorize(
				names[partcount], values[partcount], 
				device[partcount], packages[partcount],
				description[partcount]
			); 
		}
		partcount++;
	}				
}


void bomLoadData()
{
	partcount = 0;
	schematic(SCH)
	{
		SCH.sheets(S) {	
			S.parts(P) {
				bomLoadSchematic(P, S.number, "");	
			}
			S.moduleinsts(M) {
				M.module.parts(P){
					bomLoadSchematic(P, S.number, M.name + ":");
				}
			}		
		}
	}
}

UL_PART bomGetPartByName(string name)
{
	schematic(SCH)
	{
		SCH.sheets(S)
		{	
			S.parts(P)
			{
				if(P.name == name)
				{
					return P;
				}
			}
		}
	}	
}

void bomUpdatePart(int selected, int mode)
{
	int found = 0;

	for(int i = 0; i < partcount; i++)
	{
		if(	(mode == 0 && names[i] == names[selected]) || 
			(mode == 1 && values[i] == values[selected] && packages[i] == packages[selected]) || 
			(mode == 2 && values[i] == values[selected] ||
			(mode == 3 && packages[i] == packages[selected])) 
		)
		{
			manufacturer[i] = manufacturer[selected];
			part_no[i]		= part_no[selected];
			distributor[i] 	= distributor[selected];
			order_no[i] 	= order_no[selected];
			price[i] 		= price[selected];
			prices[i]		= prices[selected];
			min_qty[i] 		= min_qty[selected];
			qty_mul[i] 		= qty_mul[selected];
			datasheet[i]	= datasheet[selected];
			per_pkg[i] 		= per_pkg[selected];
			available[i]	= available[selected];
			note[i]			= note[selected];
			category[i]		= category[selected];

			found = 1;
		}	
		if(mode == 10 && distributor[i] == distributor[selected] && order_no[i] == order_no[selected])
		{
			price[i] 		= price[selected];
			prices[i]		= prices[selected];
			min_qty[i] 		= min_qty[selected];
			qty_mul[i] 		= qty_mul[selected];
			datasheet[i]	= datasheet[selected];
			per_pkg[i] 		= per_pkg[selected];
			available[i]	= available[selected];

			found = 1;
		}

	}
}

int bomMatchModuleName(string partname, string name, string prefix){
	if(prefix == "" && partname == name) {
		return 1;
	}

	if(prefix != ""){
		schematic(SCH){
			SCH.sheets(S){	
				S.moduleinsts(M){
					if(M.module.name == prefix){
						if( (M.name + ":" + partname) == name){
							return 1;
						}
					}
				}
			}
		}			
	}

	return 0;
}

string bomChangeSchematics(UL_PART P, string mysheet, string myprefix){
	string execute = "";

	if(names[partNr]!=(myprefix + P.name)) {	//toprvent multiparts from being set multipe times
		return execute;
	}

	//Match the first module instance
	string match_name = P.name;
	string part_name = P.name;
	if(myprefix != ""){
		match_name = myprefix + "1:" + P.name;
		part_name = P.name;
	}

	for(int i = 0; i < partcount; i++){
		if(match_name == names[i]) {
			string execute_part = "";
			if(manufacturer[i] 	!= P.attribute["MANUFACTURER"]) 		{sprintf(execute_part, "%s ATTRIBUTE %s MANUFACTURER \'%s\';\n", 		execute_part, part_name, manufacturer[i]);}
			if(part_no[i] 		!= P.attribute["PART_NO"]) 				{sprintf(execute_part, "%s ATTRIBUTE %s PART_NO \'%s\';\n", 			execute_part, part_name, part_no[i]);}
			if(distributor[i] 	!= P.attribute["DISTRIBUTOR"]) 			{sprintf(execute_part, "%s ATTRIBUTE %s DISTRIBUTOR \'%s\';\n", 		execute_part, part_name, distributor[i]);}
			if(order_no[i] 		!= P.attribute["ORDER_NO"]) 			{sprintf(execute_part, "%s ATTRIBUTE %s ORDER_NO \'%s\';\n", 			execute_part, part_name, order_no[i]);}
			if(price[i] 		!= P.attribute["PRICE"]) 				{sprintf(execute_part, "%s ATTRIBUTE %s PRICE \'%s\';\n", 				execute_part, part_name, price[i]);}
			if(prices[i] 		!= P.attribute["PRICES"]) 				{sprintf(execute_part, "%s ATTRIBUTE %s PRICES \'%s\';\n", 				execute_part, part_name, prices[i]);}
			if(min_qty[i] 		!= P.attribute["MINIMUM_QUANTITY"]) 	{sprintf(execute_part, "%s ATTRIBUTE %s MINIMUM_QUANTITY \'%s\';\n", 	execute_part, part_name, min_qty[i]);}
			if(qty_mul[i] 		!= P.attribute["QUANTITY_MULTIPLIER"]) 	{sprintf(execute_part, "%s ATTRIBUTE %s QUANTITY_MULTIPLIER \'%s\';\n", execute_part, part_name, qty_mul[i]);}
			if(datasheet[i] 	!= P.attribute["DATASHEET"]) 			{sprintf(execute_part, "%s ATTRIBUTE %s DATASHEET \'%s\';\n", 			execute_part, part_name, datasheet[i]);}
			if(per_pkg[i] 		!= P.attribute["PARTS_PER_PACKAGE"]) 	{sprintf(execute_part, "%s ATTRIBUTE %s PARTS_PER_PACKAGE \'%s\';\n", 	execute_part, part_name, per_pkg[i]);}
			if(available[i] 	!= P.attribute["AVAILABLE_QUANTITY"]) 	{sprintf(execute_part, "%s ATTRIBUTE %s AVAILABLE_QUANTITY \'%s\';\n", 	execute_part, part_name, available[i]);}
			if(note[i] 			!= P.attribute["NOTE"]) 				{sprintf(execute_part, "%s ATTRIBUTE %s NOTE \'%s\';\n", 				execute_part, part_name, note[i]);}
			if(category[i] 		!= strtol(P.attribute["CATEGORY"]))		{sprintf(execute_part, "%s ATTRIBUTE %s CATEGORY \'%d\';\n", 			execute_part, part_name, category[i]);}		
			if(populate[i] 		!= P.attribute["POPULATE"])				{sprintf(execute_part, "%s ATTRIBUTE %s POPULATE \'%s\';\n", 			execute_part, part_name, populate[i]);}
			
			if(execute_part != ""){
				sprintf(execute, "%s EDIT %s;\n%s",  execute, mysheet, execute_part);
			}
		}
	}
	partNr++;
	return execute;
}


string bomUpdateChanges()
{
	string execute = "";
	sprintf(execute, "CHANGE DISPLAY OFF;\n");
	sprintf(execute, "%sSET CONFIRM YES;\n",execute);

	string mysheet = "";

	partNr=0;

	schematic(SCH){
		SCH.sheets(S){	
			S.parts(P){
				sprintf(mysheet, ".s%d", S.number);
				execute += bomChangeSchematics(P, mysheet, "");
			}
		}
		SCH.modules(M) {
			M.parts(P){
				sprintf(mysheet, "%s.mod", M.name + ":");
				execute += bomChangeSchematics(P, mysheet, M.name);
			}
		}
	}
	return execute;
}

int bomCountPartsWithSameOrderNo(string pdistributor, string porder_no)
{
	int mpartcount = 0;

	for(int i = 0; i < partcount; i++)
	{
		if(distributor[i] == pdistributor && order_no[i] == porder_no){mpartcount++;}
	}
	return mpartcount;	
}
