/************************************************************/
/* HTL_Export3_Measure.ulp                                  */
/* Bemaßt das Board basierend auf den Dimension Layer       */
/* und basierend auf den Bohrungen                          */
/************************************************************/
/* (c) Copyright 2009, Bernhard Wörndl-Aichriedler          */
/* xDevelop OG - Hardware Developer			*/
/* E-Mail: bwa@berniwa.com (bwa@xdevelop.at)                */
/* Homepage: www.berniwa.com (www.xdevelop.at)              */
/************************************************************/
/* Die Verwendung, das Kopieren bzw. die Weiterverbreitung  */
/* dieses ULP sind nur nach ausdrücklicher Erlaubnis des    */
/* Autors gestattet! 				*/
/************************************************************/
/* Letzte Änderung am 28.01.2009                            */
/* Version 2.0 (in Export 3.3)                              */
/************************************************************/
/* Letzte Änderung am 14.12.2009                            */
/* Version 3.0 (in Export 4)                                */
/************************************************************/

if (!board) {
   dlgMessageBox( ":This program requires the board editor.");
   exit(1);
}

real offset = 200; //Abstand der Bemaßung von der LP
real offset_label = 25; //Abstand der Bemaßung von der Linie
real width_origin = 200; //Breite des
real width_arrow = 40; //Breite des Pfeils
real length_arrow = 125; //Länge des Pfeils
real length_line = 20; //Schwanzl vom Pfeil


real length_arrow45 = length_arrow / sqrt(2);
real width_arrow45 = width_arrow / sqrt(2);
real offset_label45 = offset_label / sqrt(2);
real length_line45 = length_line / sqrt(2);

int max_x = 0;
int min_x = 0;

int max_y = 0;
int min_y = 0;

int x_measure_count = 0;
int y_measure_count = 0;
int x_measures[];
int y_measures[];


int drills_x_sorted[];
int drills_y_sorted[];
int drills_x[];
int drills_y[];
int drills_radius[];

int drill_count = 0;

int initialized = 0;
int update = 0;

string scr_name, prj_path;

void setCoordinates(int x, int y) {
	if(!initialized) {
		max_x = x;
		min_x = x;
		max_y = y;
		min_y = y;
		initialized = 1;
	}

	if(x < min_x) {
		min_x = x;
	}
	if(y < min_y) {
		min_y = y;
	}
	if(y > max_y) {
		max_y = y;	
	}
	if(x > max_x) {
		max_x = x;	
	}
}

real realLength(real value) {
	string data = "";
	sprintf(data, "%1.1f", value);
	return (strlen(data) * 50 - 20);	
}

int getMaxX(int y) {
	int x, initialized = 0;
	for(int i = 0; i < drill_count; i++) {
		if(drills_y[i] == y) {
			if(initialized == 0) {
				initialized = 1;
				x = drills_x[i];
			}
			if(drills_x[i] > x) {
				x = drills_x[i];
			}
		}
	}
	return x;
}

int getMaxY(int x) {
	int y, initialized = 0;
	for(int i = 0; i < drill_count; i++) {
		if(drills_x[i] == x) {
			if(initialized == 0) {
				initialized = 1;
				y = drills_y[i];
			}
			if(drills_x[i] > y) {
				y = drills_y[i];
			}
		}
	}
	return y;
}

string generateArrow(real x, real y, int degree) {
	string data = "";
	
	real x1, y1, x2, y2, ax, ay;
	
	if(degree % 90 == 0) {
		int deg = degree / 90;

		if(deg % 2 == 0) {
			x1 = x + length_arrow * (deg == 0) - length_arrow * (deg == 2) ;
			y1 = y - (width_arrow / 2);			

			x2 = x1;
			y2 = y + (width_arrow / 2);
		}
		else {
			x1 = x - (width_arrow / 2);
			y1 = y + length_arrow * (deg == 1) - length_arrow * (deg == 3);

			x2 = x + (width_arrow / 2);
			y2 = y1;
		}
	}
	else if(degree % 45 == 0) {
		int deg = (degree  - 45)/ 90;

		if(deg % 2 == 0) {
			int direction = (deg == 0)?1:-1;			

			x1 = x + length_arrow45 * direction + (width_arrow45 / 2);
			y1 = y + length_arrow45 * direction - (width_arrow45 / 2);			

			x2 = x + length_arrow45 * direction - (width_arrow45 / 2);
			y2 = y + length_arrow45 * direction + (width_arrow45 / 2);
		}
		else {
			int direction = (deg == 1)?1:-1;			

			x1 = x - length_arrow45 * direction - (width_arrow45 / 2);
			y1 = y + length_arrow45 * direction - (width_arrow45 / 2);			

			x2 = x - length_arrow45 * direction + (width_arrow45 / 2);
			y2 = y + length_arrow45 * direction + (width_arrow45 / 2);
		}
	}

	sprintf(data, data + "POLYGON 4 5 (%f %f) (%f %f) (%f %f) (%f %f);\n", x, y, x1 , y1, x2 , y2, x, y);

	//dlgMessageBox(data);
	return data;
}
string generateMeasureY(int y, int paint_line, int mirror) {
	int add_y = 1; 	

	for(int i = 0; i < y_measure_count; i++) {
		if(y_measures[i] == y) {
			add_y = 0;
		}
	}
	
	real line_y = u2mil(min_y) - offset * (x_measure_count + 1);
	real line_x = 0;

	if(!mirror) {
		line_x = u2mil(min_x) - offset * (y_measure_count + 1);

	}
	else {
		line_x = u2mil(max_x) + offset * (y_measure_count + 1);		
	}

	string tmp = "";
	real text_width_vertical, text_width_horizontal;
	text_width_vertical = realLength(u2mm(y - min_y));
	
	string data = "";

	

	if(add_y) {
		y_measures[y_measure_count++] = y;
		real distance = u2mil(y - min_y);
	
		sprintf(data, data + "WIRE 4 5 (%f %f) (%f %f);\n", line_x - (width_origin / 2) , u2mil(min_y) , line_x + (width_origin / 2) , u2mil(min_y) );
		sprintf(data, data + "WIRE 4 5 (%f %f) (%f %f);\n", line_x - (width_origin / 2) , u2mil(y) , line_x + (width_origin / 2) , u2mil(y) );	


		if(distance < 2*length_arrow) {
			sprintf(data, data + generateArrow(line_x, u2mil(min_y), 270));
			sprintf(data, data + "WIRE 4 5 (%f %f) (%f %f);\n", line_x , u2mil(min_y) - length_arrow - length_line, line_x, u2mil(y) + length_arrow + length_line + realLength(u2mm(y - min_y)));
			sprintf(data, data + generateArrow(line_x, u2mil(y) , 90));
			if(!mirror) {
				sprintf(data, data + "TEXT '%1.1f' R90 (%f %f);\n", u2mm(y - min_y), line_x - offset_label , u2mil(y) + length_arrow + offset_label);
			}
			else {
				sprintf(data, data + "TEXT '%1.1f' MR90 (%f %f);\n", u2mm(y - min_y), line_x + offset_label , u2mil(y) + length_arrow + offset_label);	
			}
		}
		else {
			sprintf(data, data + generateArrow(line_x, u2mil(min_y), 90));
			sprintf(data, data + "WIRE 4 5 (%f %f) (%f %f);\n", line_x , u2mil(min_y), line_x, u2mil(y));
			sprintf(data, data + generateArrow(line_x, u2mil(y) , 270));
			
			if(!mirror) {
				sprintf(data, data + "TEXT '%1.1f' R90 (%f %f);\n", u2mm(y - min_y), line_x - offset_label ,u2mil(min_y) + u2mil((y - min_y)/2)  - (text_width_vertical/2));
			}
			else {
				sprintf(data, data + "TEXT '%1.1f' MR90 (%f %f);\n", u2mm(y - min_y), line_x + offset_label ,u2mil(min_y) + u2mil((y - min_y)/2)  - (text_width_vertical/2));				
			}
		}
		
		if(paint_line) {
			sprintf(data, data + "WIRE 4 5 (%f %f) (%f %f);\n", line_x ,u2mil(min_y), u2mil(min_x), u2mil(min_y));
			sprintf(data, data + "WIRE 4 5 (%f %f) (%f %f);\n", line_x ,u2mil(y), u2mil(getMaxX(y)), u2mil(y));
		}
	}

	return data;
}



string generateMeasureX(int x, int paint_line, int mirror) {
	int add_x = 1; 	

	for(int i = 0; i < x_measure_count; i++) {
		if(x_measures[i] == x) {
			add_x = 0;
		}
	}
	
	real line_x = u2mil(min_x) - offset * (y_measure_count + 1);
	real line_y = u2mil(min_y) - offset * (x_measure_count + 1);

	string tmp = "";
	real text_width_vertical, text_width_horizontal;
	text_width_horizontal = realLength(u2mm(x - min_x));	
	string data = "";
	
	if(add_x) {
		x_measures[x_measure_count++] = x;
		real distance = u2mil(x - min_x);


		sprintf(data, data + "WIRE 4 5 (%f %f) (%f %f);\n", u2mil(min_x), line_y - (width_origin / 2), u2mil(min_x), line_y + (width_origin / 2));
		sprintf(data, data + "WIRE 4 5 (%f %f) (%f %f);\n", u2mil(x), line_y - (width_origin / 2), u2mil(x), line_y + (width_origin / 2));
		
		if(distance < 2*length_arrow) {
			sprintf(data, data + "WIRE 4 5 (%f %f) (%f %f);\n", u2mil(min_x) - length_arrow - length_line, line_y, u2mil(x) + length_arrow + length_line + realLength(u2mm(x - min_x)), line_y);
			sprintf(data, data + generateArrow(u2mil(min_x), line_y, 180));
			sprintf(data, data + generateArrow(u2mil(x), line_y, 0));
			if(!mirror) {
				sprintf(data, data + "TEXT '%1.1f' R0 (%f %f);\n", u2mm(x - min_x), u2mil(x) + length_arrow + offset_label, line_y + offset_label);
			}
			else {
				sprintf(data, data + "TEXT '%1.1f' MR0 (%f %f);\n", u2mm(x - min_x), u2mil(x) + length_arrow + offset_label + text_width_horizontal, line_y + offset_label);
			}
		}
		else {
			sprintf(data, data + "WIRE 4 5 (%f %f) (%f %f);\n", u2mil(min_x), line_y, u2mil(x), line_y);
			sprintf(data, data + generateArrow(u2mil(min_x), line_y, 0));
			sprintf(data, data + generateArrow(u2mil(x), line_y, 180));
			if(!mirror) {
				sprintf(data, data + "TEXT '%1.1f' R0 (%f %f);\n", u2mm(x - min_x), u2mil(min_x) + u2mil((x - min_x)/2) - (text_width_horizontal/2), line_y + offset_label);
			}
			else {
				sprintf(data, data + "TEXT '%1.1f' MR0 (%f %f);\n", u2mm(x - min_x), u2mil(min_x) + u2mil((x - min_x)/2) + (text_width_horizontal/2), line_y + offset_label);
			}	
		}
		
		if(paint_line) {
			sprintf(data, data + "WIRE 4 5 (%f %f) (%f %f);\n", u2mil(min_x) , line_y, u2mil(min_x), u2mil(min_y));
			sprintf(data, data + "WIRE 4 5 (%f %f) (%f %f);\n", u2mil(x), line_y, u2mil(x), u2mil(getMaxY(x)));
		}
		
	}

	return data;
}

string generateDiameter(int x, int y, int radius)
{
	string data = "";
	if(radius) {
		real str_len45 = realLength(u2mm(radius) * 2) / sqrt(2);
		int quadrant = (y > (((max_y - min_y) / 2) + min_y)) + (x > (((max_x - min_x) / 2) + min_x)) * 2;

		if(quadrant == 0) {
			real right_top_x = u2mil(x) + (u2mil(radius) / sqrt(2)), right_top_y = u2mil(y) + (u2mil(radius) / sqrt(2)), left_bot_x = u2mil(x)- (u2mil(radius) / sqrt(2)), left_bot_y = u2mil(y) - (u2mil(radius) / sqrt(2));
		
			sprintf(data, data + "WIRE 4 5 (%f %f) (%f %f);\n", u2mil(x-radius) - length_arrow45 - length_line45, u2mil(y-radius) - length_arrow45 - length_line45, u2mil(x+radius) + length_arrow45 + length_line45 + str_len45, u2mil(y+radius) + length_arrow45 + length_line45 + str_len45);
			sprintf(data, data + generateArrow(right_top_x, right_top_y, 45));
			sprintf(data, data + generateArrow(left_bot_x, left_bot_y, 225));
			sprintf(data, data + "TEXT '%1.1f' R45 (%f %f);\n", u2mm(radius) * 2, right_top_x + length_arrow45, right_top_y + length_arrow45 + offset_label45);
		}
		else if(quadrant == 1) {
			real right_bot_x = u2mil(x) + (u2mil(radius) / sqrt(2)), right_bot_y = u2mil(y) - (u2mil(radius) / sqrt(2)), left_top_x = u2mil(x) - (u2mil(radius) / sqrt(2)), left_top_y = u2mil(y) + (u2mil(radius) / sqrt(2));
		
			sprintf(data, data + "WIRE 4 5 (%f %f) (%f %f);\n", u2mil(x-radius) - length_arrow45 - length_line45, u2mil(y+radius) + length_arrow45 + length_line45, u2mil(x+radius) + length_arrow45 + length_line45 + str_len45, u2mil(y-radius) - length_arrow45 - length_line45 - str_len45);
			sprintf(data, data + generateArrow(right_bot_x, right_bot_y, 315));
			sprintf(data, data + generateArrow(left_top_x, left_top_y, 135));
			sprintf(data, data + "TEXT '%1.1f' R-45 (%f %f);\n", u2mm(radius) * 2, right_bot_x + length_arrow45 + offset_label45, right_bot_y - length_arrow45);
			
		}
		else if(quadrant == 2) {
			real right_bot_x = u2mil(x) + (u2mil(radius) / sqrt(2)), right_bot_y = u2mil(y) - (u2mil(radius) / sqrt(2)), left_top_x = u2mil(x) - (u2mil(radius) / sqrt(2)), left_top_y = u2mil(y) + (u2mil(radius) / sqrt(2));
		
			sprintf(data, data + "WIRE 4 5 (%f %f) (%f %f);\n", u2mil(x-radius) - length_arrow45 - length_line45 - str_len45, u2mil(y+radius) + length_arrow45 + length_line45 + str_len45, u2mil(x+radius) + length_arrow45 + length_line45, u2mil(y-radius) - length_arrow45 - length_line45);
			sprintf(data, data + generateArrow(right_bot_x, right_bot_y, 315));
			sprintf(data, data + generateArrow(left_top_x, left_top_y, 135));
			sprintf(data, data + "TEXT '%1.1f' R-45 (%f %f);\n", u2mm(radius) * 2, left_top_x - length_arrow45 - str_len45, left_top_y + length_arrow45 + str_len45 + offset_label45);
			
		}  
		else if(quadrant == 3) {
			real right_top_x = u2mil(x) + (u2mil(radius) / sqrt(2)), right_top_y = u2mil(y) + (u2mil(radius) / sqrt(2)), left_bot_x = u2mil(x)- (u2mil(radius) / sqrt(2)), left_bot_y = u2mil(y) - (u2mil(radius) / sqrt(2));
		
			sprintf(data, data + "WIRE 4 5 (%f %f) (%f %f);\n", u2mil(x-radius) - length_arrow45 - length_line45 - str_len45, u2mil(y-radius) - length_arrow45 - length_line45 -  str_len45, u2mil(x+radius) + length_arrow45 + length_line45, u2mil(y+radius) + length_arrow45 + length_line45);
			sprintf(data, data + generateArrow(right_top_x, right_top_y, 45));
			sprintf(data, data + generateArrow(left_bot_x, left_bot_y, 225));
			sprintf(data, data + "TEXT '%1.1f' R45 (%f %f);\n", u2mm(radius) * 2, left_bot_x - length_arrow45 - str_len45 -  offset_label45, left_bot_y - length_arrow45 - str_len45);
		}
		
		sprintf(data, data + "CIRCLE 2 (%f %f) (%f %f);\n", u2mil(x), u2mil(y), u2mil(x - radius), u2mil(y));
	}
	return data;
}

void writeScr() {
	real line_x = u2mil(min_x) - offset;
	real line_y = u2mil(min_y) - offset;

	output(scr_name,"wt") {
		printf("OPEN \'%sfabrication.lbr\';\n", prj_path);
		printf("EDIT measure.pac;\n");
		printf("GRID mil FINEST;\n");
		printf("CHANGE layer 48;\n");
		printf("SET Wire_Bend 2;\n");

		printf("CHANGE SIZE 70;\n");
		printf("CHANGE FONT PROPORTIONAL;\n");
		printf("CHANGE ALIGN BOTTOM LEFT;\n");

		printf("GROUP ALL;\n");
		printf("DELETE (>0 0);\n");

		printf(generateMeasureX(max_x, 0, 0));
		printf(generateMeasureY(max_y, 0, 0));
		
		x_measure_count = 0;
		y_measure_count = 0;

		
		printf("LAYER 112 MEASURE_BOTTOM;\n");
		printf(generateMeasureX(max_x, 0, 1));
		printf(generateMeasureY(max_y, 0, 1));

		x_measure_count = 0;
		y_measure_count = 0;

		printf("LAYER 111 MEASURE;\n");
		printf("CHANGE layer 111;\n");

		for(int i = 0; i < drill_count; i++) {
			printf(generateMeasureX(drills_x_sorted[i], 1, 0));
			printf(generateMeasureY(drills_y_sorted[i], 1, 0));
			printf(generateDiameter(drills_x[i], drills_y[i], drills_radius[i]));
		}
		
		printf("WRITE '%sfabrication.lbr';\n", prj_path);
		printf("CLOSE '%sfabrication.lbr';\n", prj_path);
		printf("USE '%sfabrication.lbr';\n", prj_path);
		if(update) {
			printf("UPDATE '%sfabrication.lbr';\n", prj_path);
			printf("DELETE MEASURE;\n");
		}
		printf("ADD 'MEASURE' MEASURE R0 (0 0);\n");
		
	}
}

board(B) {
	prj_path = filedir(B.name);
	scr_name = prj_path+"tmp.scr";

 	B.wires(W) {
		if(W.layer == 20) {
			if(W.arc) {
				setCoordinates(W.arc.x1, W.arc.y1);
				setCoordinates(W.arc.x2, W.arc.y2);
				
				int angle = W.arc.angle2 - W.arc.angle1;
				
				int set_elements = round(angle/90);
				int start_element = round(W.arc.angle1/90);
				start_element = start_element % 4;

				/*string tmp = "";
				sprintf(tmp, "%f %f %d %d", W.arc.angle1, W.arc.angle2, start_element, set_elements);
				dlgMessageBox(tmp);*/
				
				for(int i = start_element; i < (start_element + set_elements); i++) {
					if(i == 0) {
						setCoordinates(W.arc.xc - W.arc.radius, W.arc.y1);
					}
					else if(i == 1) {
						setCoordinates(W.arc.x2, W.arc.yc + W.arc.radius);
					}
					else if(i == 2) {
						setCoordinates(W.arc.xc + W.arc.radius, W.arc.y1);
					}
					else if(i == 3) {
						setCoordinates(W.arc.x2, W.arc.yc - W.arc.radius);
					}
				}
			}
			else {
				setCoordinates(W.x1, W.y1);
				setCoordinates(W.x2, W.y2);
			}
		}
	}
	B.circles(C) {
		if(C.layer == 20) {
			setCoordinates(C.x + C.radius, C.y + C.radius);
			setCoordinates(C.x - C.radius, C.y - C.radius);
		}
	}
	B.elements(E) {
		if(E.name == "MEASURE") {	
			update = 1;
		}
	}
	B.holes(D) {
		drills_x[drill_count] = D.x;
		drills_y[drill_count] = D.y;
		drills_radius[drill_count++] = D.drill / 2;
	}
	B.signals(S) {
		S.vias(D) {
			if(u2mm(D.drill) > 2) {//Use Vias > 2.0mm as mounting holes
				drills_x[drill_count] = D.x;
				drills_y[drill_count] = D.y;
				drills_radius[drill_count++] = D.drill / 2;
			}		
		}
	}
}


drills_x[drill_count] = max_x;
drills_y[drill_count] = max_y;
drills_radius[drill_count++] = 0;
for(int ii = 0; ii < drill_count;ii++) {
	drills_x_sorted[ii] = drills_x[ii];
}
for(ii = 0; ii < drill_count; ii++) {
	drills_y_sorted[ii] = drills_y[ii];
}

sort(drill_count, drills_x_sorted);
sort(drill_count, drills_y_sorted);

writeScr();
exit("; SCR '" + scr_name + "';\n");
