string order[] = {
	"construction",
	"fabrication",
	"reference",
	"l01-top",
	"l02",
	"l03",
	"l04",
	"l05",
	"l06",
	"l07",
	"l08",
	"l09",
	"l10",
	"l11",
	"l12",
	"l13",
	"l14",
	"l15",
	"l16-bot",
	"parts-top",
	"parts-bottom",
	"stop-top",
	"stop-bottom",
	"paste-top",
	"paste-bottom",
	"pcb-top",
	"pcb-bot"
};

void main(){
	int dateFolder = strtol(argv[1]);
	string outputFile=argv[2]+".pdf";
	int sch = strtol(argv[4]);
	int bom = strtol(argv[5]);


	int i = strstr(outputFile,"/");

	while(i>=0){
		outputFile[i]='\\';
		i = strstr(outputFile,"/",i);
	}

	if(system("CMD.EXE /C echo off && pdftk --version")==-1){
		dlgMessageBox(":To merge the pdf-files we use pdftk_server.<br>"+
						"You can get this tool <a href=\"https://www.pdflabs.com/tools/pdftk-server/\">here</a>.");
		exit("");
	}


	string path = filedir(outputFile);
	string tmpFile = path + "tmp.pdf";

	//dlgMessageBox(argv[2]);

	output(argv[3],"at"){
		//printf("echo on\n");

		printf("%s:\n",strsub(path,0,1));
		printf("cd \"%s\"\n",path);//W:\Tobias\Projects\fpga\docu\2019-09-03\pdf
		
		printf("pdftk ");

		if (!dateFolder){
			if(filesize(filesetext(outputFile,"-schematic.pdf"))){
				printf("*schematic.pdf ");
			}
			tmpFile=outputFile;
		}

		for (i = 0; order[i]; i++){
			if(filesize(filesetext(outputFile,("-"+order[i]+".pdf")))) {
				printf("*%s.pdf ",order[i]);
			}
		}

		printf("cat output \"%s\"\n",tmpFile);

		if(dateFolder){
			printf("del \"%s*.pdf\"\n",filesetext(filename(outputFile),""));
			printf("cd ..\n");				//W:\Tobias\Projects\fpga\docu\2019-09-03

			if (bom||sch) {
				printf("pdftk ");
				if (sch){
					printf("*-schematic.pdf ");
				}

				printf("\"%s\" ", tmpFile);

				if (bom) {
					printf("*-bom.pdf ");
				}

				printf("cat output \"%s\"\n",outputFile);
				printf("del \"%s\"\n", tmpFile);

				if (bom) {
					printf("del *-bom.pdf\n");
				}
			}
			else {
				printf("ren \"%s\" \"%s\"\n",tmpFile,filename(outputFile));
			}

			printf("copy \"%s\" \"%s\"\n",outputFile,filename(outputFile));
			printf("rd /S /Q pdf\n");
		}
		else {
			for(i=0; order[i]; i++){
				if(filesize(filesetext(outputFile,("-"+order[i]+".pdf")))) {
					printf("del *%s.pdf\n",order[i]);
				}
			}
		}

		//printf("pause\n");
	}
}
