/************************************************************/
/* HTL_Export4_Apd.ulp                                      */
/* - Generiert Daten  für da Programm 			*/
/*   AutoProjectDocumentation von Timo Huemer 		*/
/*   (timo.huemer@hotmail.com)                              */
/************************************************************/
/* (c) Copyright 2009, Bernhard Wörndl-Aichriedler          */
/* xDevelop OG - Hardware Developer			*/
/* E-Mail: bwa@berniwa.com (bwa@xdevelop.at)                */
/* Homepage: www.berniwa.com (www.xdevelop.at)              */
/************************************************************/
/* Die Verwendung, das Kopieren bzw. die Weiterverbreitung  */
/* dieses ULP sind nur nach ausdrücklicher Erlaubnis des    */
/* Autors gestattet! 				*/
/************************************************************/
/* Letzte Änderung am 14.12.2009                            */
/* Version 1.0 (in Export 4.0)                              */
/************************************************************/

int BMP_bfOffBits 	= 10;
int BMP_biWidth 	= 18;
int BMP_biHeight	= 22;

int output_lt = 0, output_pt = 0, output_lb = 0, output_pb = 0, output_drl = 0, output_cs = 0;
string output_file_lb, output_file_lt, output_file_pb, output_file_pt, output_file_cs, output_file_drl;

char bmpData[];
int bmpWidth = 0, bmpHeight = 0;

int bmpReadInt(int offset)
{
	int value = 0;
			
	for(int i = 0; i < 4; i++) 
	{
		value |= bmpData[offset + i] << (i*8);
	}

	return value;	
}

void bmpReadSize(string ifilename)
{
	
	int nBytes = fileread(bmpData, ifilename);

  	/*
  		Read status information
  	*/
  	bmpWidth = bmpReadInt(BMP_biWidth);
  	bmpHeight = bmpReadInt(BMP_biHeight);
}

string getFilename(string basename, string ends_with)
{
	return filesetext(basename,ends_with);
}

void apdProcess()
{
	string ofilename = "";

	if(argc > 1)
	{
		ofilename = argv[1];	
	}
	for(int i = 2; i < argc; i++)
	{
		if(argv[i] == "-lb")
		{
			output_lb = 1;
		}
		else if(argv[i] == "-lt")
		{
			output_lt = 1;
		}
		else if(argv[i] == "-pt")
		{
			output_pt = 1;
		}
		else if(argv[i] == "-pb")
		{
			output_pb = 1;
		}
		else if(argv[i] == "-drl")
		{
			output_drl = 1;
		}
		else if(argv[i] == "-cs")
		{
			output_cs = 1;
		}
	}	

	output_file_lb = getFilename(ofilename, "-layout-bot.bmp");
	output_file_lt = getFilename(ofilename, "-layout-top.bmp");
	output_file_pb = getFilename(ofilename, "-parts-bot.bmp");
	output_file_pt = getFilename(ofilename, "-parts-top.bmp");
	output_file_cs = getFilename(ofilename, "-construction.bmp");
	output_file_drl = getFilename(ofilename, "-drills.bmp");


	output(ofilename, "wt")
	{
		if(output_lb)
		{
			bmpReadSize(output_file_lb);
			printf("layout-bot\t%s\t%d\t%d\n",output_file_lb, bmpWidth, bmpHeight);
		}
		if(output_lt)
		{
			bmpReadSize(output_file_lt);
			printf("layout-top\t%s\t%d\t%d\n",output_file_lt, bmpWidth, bmpHeight);
		}
		if(output_pb)
		{
			bmpReadSize(output_file_pb);
			printf("parts-top\t%s\t%d\t%d\n",output_file_pb, bmpWidth, bmpHeight);
		}
		if(output_pt)
		{
			bmpReadSize(output_file_pt);
			printf("parts-bot\t%s\t%d\t%d\n",output_file_pt, bmpWidth, bmpHeight);
		}
		if(output_cs)
		{
			bmpReadSize(output_file_cs);
			printf("construction\t%s\t%d\t%d\n",output_file_cs, bmpWidth, bmpHeight);
		}	
		if(output_drl)
		{
			bmpReadSize(output_file_drl);
			printf("drills\t%s\t%d\t%d\n",output_file_drl, bmpWidth, bmpHeight);
		}
	}	
}


apdProcess();
