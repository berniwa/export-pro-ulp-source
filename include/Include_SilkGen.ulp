/************************************************************/
/* HTLExportPro_SilkGen.ulp                                 */
/* - Generiert den Silkscreen des Boardes auf einem         */
/*   separaten Layer                                        */
/************************************************************/
/* (c) Copyright 2011, Bernhard Wörndl-Aichriedler          */
/* E-Mail: bwa@berniwa.com                                  */
/* Homepage: www.berniwa.com                                */
/************************************************************/
/* Letzte Änderung am 20.02.2011                            */
/* Version 1                                                */
/************************************************************/

#usage "<b>Generate new silk screen layers</b>\n"
       "<p>"
       "Some board manufacturers specify a minimum width for silk "
       "screen lines (eg. Olimex requires 10 mil). The EAGLE "
       "libraries normally contain 5 mil wide silk screen lines. "
       "This ULP creates two new silk screen layers with all the "
       "usual silk screen elements on them, but with the line widths "
       "modified to fit within the specified minimum and maximum "
       "width limits."
       "<p>"
       "#s are also changed. The new ratio is set to the minimum "
       "needed to achieve the required line width. If the original "
       "text ratio is greater than the minimum required, it is not "
       "changed. Silk screen texts are always rendered using the "
       "vector font regardless of the input font style."
       "<p>"
       "Two new layers called _tsilk and _bsilk will be created and "
       "the new silk screens will be drawn on those layers. When "
       "generating GERBER data for the silk screens, remember to "
       "use _tsilk and _bsilk instead of the usual silk screen "
       "layers."
       "<p>"
       "<author>Original authors: Richard Hammerl 26-05-1998. "
       "Changed for EAGLE 4.0 26-02-2002, support@cadsoft.de. "
       "Fixed for EAGLE 4.11, OLIMEX special 04-11-2003, Y.Onodera. "
       "Further fixed and modified by Antti Arola 11.03.2005. "
       "Several features by Bill Westfield. "
       "Many improvements and cleanups by Alex Holden 21-03-2006"
       "Edited to be used in batch mode by Bernhard Wörndl-Aichriedler 20.02.2010"
       "</author>"

// THIS PROGRAM IS PROVIDED AS IS AND WITHOUT WARRANTY OF ANY KIND, EXPRESSED
// OR IMPLIED.

// You can change these values to modify the ULP's behaviour:
int dimensionnum = 123;          // Number of the dimension silkscreen layer.
string dimensionname = "_dimension"; // Name of the dimension silkscreen layer.
string dimensioncolor = "20";// Color of the dimension silkscreen layer.
int backgroundnum = 124;          // Number of the background silkscreen layer.
string backgroundname = "_background"; // Name of the background silkscreen layer.
string backgroundcolor = "21";// Color of the background silkscreen layer.
int emptynum = 127;          // Number of the empty silkscreen layer.
string emptyname = "_empty"; // Name of the empty silkscreen layer.
string emptycolor = "20";// Color of the empty silkscreen layer.
real minwidth = 0.1;   // Default minimum silk screen line width (mils).
real maxwidth = 0.0;         // Default maximum width (0 = no limit).
int delete_old = 1;          // Whether to clear old silk screen layers.

int copy_tdimension = 1;      		   // Whether to copy the Dimension layer.
int hatch_fill = 0;          // Whether to use the hatch fill style.
int no_fill = 0;             // Whether to draw rectangles and discs in outline.
int hide_sources = 1;        // Whether to hide the source layers.
int disable_undo = 0;        // Whether to disable undo during script execution.
int show_script = 0;         // Whether to show the script before executing it.

////////////////////////////////////////////////////////////////////////////////
///// Don't change anything below here unless you know what you're doing. //////
////////////////////////////////////////////////////////////////////////////////

real cursize = -1.0;
int clearsilks = 0, saved_grid_unit = GRID_UNIT_MIL;
string saved_visible_layers[], textorientation, h, cmd;
int destlayer, curdestlayer = -1, curlinestyle = -1, curratio = -1;

int wX1[], wY1[], wX2[], wY2[], wRad[], wWid[];
int index = 0;

void header() {
  string s;
  if(disable_undo) cmd += "set undo_log off;\n";
  h = "";sprintf(h, "layer %d %s;\n", dimensionnum, dimensionname);cmd += h;
  h = "";sprintf(h, "layer %d %s;\n", backgroundnum, backgroundname);cmd += h;
  h = "";sprintf(h, "layer %d %s;\n", emptynum, emptyname);cmd += h;
  h = "";sprintf(h, "set color_layer %d %s;\n", dimensionnum, dimensioncolor);cmd += h;
  h = "";sprintf(h, "set color_layer %d %s;\n", backgroundnum, backgroundcolor);cmd += h;
  h = "";sprintf(h, "set color_layer %d %s;\n", emptynum, emptycolor);cmd += h;
  cmd += "set wire_bend 2;\n";
  cmd += "change font vector;\n";
  if(hatch_fill) s = "hatch";
  else s = "solid";
  h = "";sprintf(h, "change pour %s;\n", s);cmd += h;
  cmd += "grid mm;\n";
}

real calctextwidth(int size, int ratio) {
  return u2mm(size) * (ratio/100.0);
}

int calctextratio(int size, real width) {
  if(size == 0)
  {
	return 8;
  }
  return ceil((width / u2mm(size)) * 100);
}

void set_layer() {
  if(destlayer != curdestlayer) {
    h = "";sprintf(h, "layer %d;\n", destlayer);cmd += h;
    curdestlayer = destlayer;
  }
}

void set_line_style(int newlinestyle) {
  string s;
  if(newlinestyle != curlinestyle) {
    switch(newlinestyle) {
      case WIRE_STYLE_LONGDASH:
        s = "longdash";
        break;
      case WIRE_STYLE_SHORTDASH:
        s = "shortdash";
        break;
      case WIRE_STYLE_DASHDOT:
        s = "dashdot";
        break;
      default:
        s = "continuous";
    }
    h = "";sprintf(h, "change style %s;\n", s);cmd += h;
    curlinestyle = newlinestyle;
  }
}

void set_ratio(int newratio) {
  if(newratio != curratio) {
    h = "";sprintf(h, "change ratio %d;\n", newratio);cmd += h;
    curratio = newratio;
  }
}

void set_size(real newsize) {
  if(newsize != cursize) {
    h = "";sprintf(h, "change size %5.3f;\n", newsize);cmd += h;
    cursize = newsize;
  }
}

real calcwidth(int width) {
  real w = u2mm(width);
  if(minwidth && w < minwidth) return minwidth;
  else if(maxwidth && w > maxwidth) return maxwidth;
  else return w;
}

void do_wire(UL_WIRE W, int sourcelayer) {
  string style;

  if(destlayer==backgroundnum){
    if(W.arc){
      wX1[index]=W.arc.x1;
      wY1[index]=W.arc.y1;
      wX2[index]=W.arc.x2;
      wY2[index]=W.arc.y2;
      wRad[index]=W.arc.radius;
      wWid[index]=W.arc.width;
      if((W.arc.angle2-W.arc.angle1)>180){
        wX2[index]=((W.arc.x1-W.arc.x2)/2)+W.arc.x2;
        wX2[index]=W.arc.xc-wX2[index];
        wY2[index]=((W.arc.y1-W.arc.y2)/2)+W.arc.y2;
        wY2[index]=W.arc.yc-wY2[index];

        real factor = W.arc.radius/sqrt(pow(wX2[index],2)+pow(wY2[index],2));

        wX2[index]*=factor;
        wX2[index]+=W.arc.xc;
        wY2[index]*=factor;
        wY2[index]+=W.arc.yc;
        index++;

        wX1[index]=wX2[index-1];
        wY1[index]=wY2[index-1];
        wX2[index]=W.arc.x2;
        wY2[index]=W.arc.y2;
        wRad[index]=wRad[index-1];
        wWid[index]=wWid[index-1];
      }
    }
    else{
      wX1[index]=W.x1;
      wY1[index]=W.y1;
      wX2[index]=W.x2;
      wY2[index]=W.y2;
      wRad[index]=0;
      wWid[index]=W.width;
    }
    
    index++;
  }
  else {
    if(W.arc) {
      if(W.arc.layer == sourcelayer) {
        set_layer();
        if ((W.arc.angle2-W.arc.angle1)>180){
          int tmpx, tmpy;

          tmpx=((W.arc.x1-W.arc.x2)/2)+W.arc.x2;
          tmpx=W.arc.xc-tmpx;
          tmpy=((W.arc.y1-W.arc.y2)/2)+W.arc.y2;
          tmpy=W.arc.yc-tmpy;

          real factor = W.arc.radius/sqrt(pow(tmpx,2)+pow(tmpy,2));

          tmpx*=factor;
          tmpx+=W.arc.xc;
          tmpy*=factor;
          tmpy+=W.arc.yc;

          sprintf(cmd,"%s wire %5.3f (%5.3f %5.3f) @%+5.3f (%5.3f %5.3f) @%+5.3f (%5.3f %5.3f);\n",cmd,
            calcwidth(W.arc.width),
            u2mm(W.arc.x1), u2mm(W.arc.y1),
            u2mm(W.arc.radius),
            u2mm(tmpx), u2mm(tmpy),
            u2mm(W.arc.radius),
            u2mm(W.arc.x2), u2mm(W.arc.y2)
          );
        }
        else {
          h = "";sprintf(h, "wire %5.3f (%5.3f %5.3f) @%+5.3f (%5.3f %5.3f);\n", 
            calcwidth(W.arc.width),
            u2mm(W.arc.x1), u2mm(W.arc.y1),
            u2mm(W.arc.radius),
            u2mm(W.arc.x2), u2mm(W.arc.y2)
          );
          cmd += h;
        }
      }
    } else {
      if(W.layer == sourcelayer) {
        set_layer();
        set_line_style(W.style);
        h = "";sprintf(h, "wire %5.3f (%5.3f %5.3f) (%5.3f %5.3f);\n",
                          calcwidth(W.width), u2mm(W.x1), u2mm(W.y1),
                          u2mm(W.x2), u2mm(W.y2));cmd += h;
      }
    }
  }
}

void do_circle(UL_CIRCLE C) {
  if(destlayer==backgroundnum){
    wX1[index]=C.x;
    wY1[index]=C.y;
    wX2[index]=C.x;
    wY2[index]=C.y;
    wRad[index]=C.radius;
    wWid[index] = 0;
    index++;
  }
  else{
    real width;

    // Circles with a width of 0 are filled.
    if(C.width == 0 && !no_fill) width = 0;
    else width = calcwidth(C.width);

    set_layer();
    h = "";sprintf(h, "circle %5.3f (%5.3f %5.3f) (%5.3f %5.3f);\n", width,
                      u2mm(C.x), u2mm(C.y), u2mm(C.x + C.radius),
                      u2mm(C.y));cmd += h;
  }
}

void do_rectangle(UL_RECTANGLE R) {
  real x1, x2, x3, x4, y1, y2, y3, y4, halfmin;
  real xt, yt, xll, xur, yll, yur, a;  /* Angle transformation for outlines */
  set_layer();
  if(no_fill) {
    set_line_style(WIRE_STYLE_CONTINUOUS);
    halfmin = minwidth / 2.0;

    xll = u2mm(R.x1) + halfmin;  /* Original LL, UR coords */
    xur = u2mm(R.x2) - halfmin;
    yll = u2mm(R.y1) + halfmin;
    yur = u2mm(R.y2) - halfmin;

    xt = xll + ((xur-xll)/2);  /* Translation params to origin */
    yt = yll + (yur-yll)/2;

    a = R.angle * (PI / 180.0);  /* Rotation in radians */

    /* First point xll, yll */
    x1 = (xt + ((xll-xt)*cos(a) - (yll-yt)*sin(a)));
    y1 = (yt + ((xll-xt)*sin(a) + (yll-yt)*cos(a)));

    /* Second point xll, yur */

    x2 = (xt + ((xll-xt)*cos(a) - (yur-yt)*sin(a)));
    y2 = (yt + ((xll-xt)*sin(a) + (yur-yt)*cos(a)));

    /* Third point xur yur */
    x3 = (xt + ((xur-xt)*cos(a) - (yur-yt)*sin(a)));
    y3 = (yt + ((xur-xt)*sin(a) + (yur-yt)*cos(a)));

    /* Forth point xur yll */
    x4 = (xt + ((xur-xt)*cos(a) - (yll-yt)*sin(a)));
    y4 = (yt + ((xur-xt)*sin(a) + (yll-yt)*cos(a)));

    h = "";sprintf(h, "wire %5.3f (%5.3f %5.3f) (%5.3f %5.3f) (%5.3f %5.3f) "
                      "(%5.3f %5.3f) (%5.3f %5.3f);\n", minwidth, x1, y1,
                      x2, y2, x3, y3, x4, y4, x1, y1);cmd += h;
  } else {
    h = "";sprintf(h, "rect R%1.0f (%5.3f %5.3f) (%5.3f %5.3f);\n", R.angle,
                   u2mm(R.x1), u2mm(R.y1), u2mm(R.x2), u2mm(R.y2));cmd += h;
  }
}

void do_polygon(UL_POLYGON P) {
  set_layer();
  P.wires(WP) {
    h = "";sprintf(h, "polygon %5.3f (%5.3f %5.3f)\n ", calcwidth(WP.width),
                      u2mm(WP.x1), u2mm(WP.y1));cmd += h;
    break;
  }
  P.wires(WP) {
    h = "";sprintf(h, " %5.3f (%5.3f %5.3f)", WP.curve, u2mm(WP.x2),
                      u2mm(WP.y2));cmd += h;
  }
  h = "";sprintf(h, ";\n");cmd += h;
}

/**
 * str_replace
 *
 * Replaces all occurrences of a substring found within a string.
 */
string str_replace(string search, string replace, string subject) {
    int lastpos = 0;
    while(strstr(subject, search, lastpos) >= 0) {
        int pos = strstr(subject, search, lastpos);
        string before = strsub(subject, 0, pos);
        string after = strsub(subject, pos + strlen(search));
        subject = before + replace + after;
        lastpos = pos + strlen(replace);
    }
    return subject;
}

void do_element(UL_ELEMENT E, int sourcelayer) {
  E.package.wires(W) if(W.layer == sourcelayer) do_wire(W, sourcelayer);
  E.package.circles(C) if(C.layer == sourcelayer) do_circle(C);
  E.package.rectangles(R) if(R.layer == sourcelayer) do_rectangle(R);
  E.package.polygons(P) if(P.layer == sourcelayer) do_polygon(P);
}

void create_via(int x, int y, int drill, int diameter_top, int diameter_bottom, int shape, real angle) {
	string h = "";
	real octagonFactor = 4.83;
	
	//Via is unfilled
	if(diameter_top == diameter_bottom && diameter_bottom > 0.0) {	
		int diameter = diameter_top;
		//Center hole
		sprintf(h, "CHANGE LAYER %s;\n", emptyname); cmd += h;
		sprintf(h, "CIRCLE 0 (%5.3f %5.3f) (%5.3f %5.3f);\n", u2mm(x), u2mm(y), u2mm(x + (drill/2)), u2mm(y)); cmd += h;
	}
}

/**
 * Transforms to coordinates to a new position
 * @param x         Relative X coordinate
 * @param y         Relative Y coordinate
 * @param r         Rotation rotation
 * @param center_x  Center X coordinate
 * @param center_y  Center Y coordinate
 * @return  x       New X coordinate (will overwrite global variable)
 * @return  y       Nex Y coordinate (will overwrite global variable)
 */
int x = 0; int y = 0;
void transform(int xi, int yi, real ri,  int center_x, int center_y){
  //Compute relative cooridinates
  int rx = xi;
  int ry = yi;

  //Get the new center coordinates
  int cx = center_x;
  int cy = center_y;

  //Transform to polar cooridnates
  real l    = sqrt((1.0*rx*rx) + (1.0*ry*ry));
  real phi  = 0.0;

  if(rx > 0){
    phi = atan((1.0*ry)/(1.0*rx));
  } else if(rx < 0 && ry >= 0){
    phi = atan((1.0*ry)/(1.0*rx)) + PI;
  } else if(rx < 0 && ry < 0){
    phi = atan((1.0*ry)/(1.0*rx)) - PI;
  } else if(rx == 0 && ry > 0){
    phi = PI/2;
  } else if(rx == 0 && ry <= 0){
    phi = -PI/2;
  }
  

  if(ri < 0){
    string tmp;
    sprintf(tmp, "Rotate %5.3f", ri);
    dlgMessageBox(tmp);
  }

  //Rotate
  phi = phi + (2.0*PI*ri/360.0);

  if(phi > 2.0*PI){
    phi = phi - 2.0*PI;
  }
  if(phi < -2.0*PI){
    phi = phi + 2.0*PI;
  }


  //Convert back cartesian
  int rx2 = l * cos(phi);
  int ry2 = l * sin(phi);

  x = cx + rx2;
  y = cy + ry2; 
}

void create_smd(int layer, int cx, int cy, int dx, int dy, real angle, int roundness) {
	string h = "";
	int rx, ry, rdx, rdy;
	
	rx = cx - (dx/2);
	ry = cy - (dy/2);
	rdx = rx + dx;
	rdy = ry + dy;
	//rx = x;
	//ry = y;
	//rdx = dx;
	//rdy = dy;
  int minlength = (dx < dy)?dx:dy;
  real radius = 1.0 * roundness / 100.0 * minlength / 2.0;

  //angle = -90;

	sprintf(h, "CHANGE LAYER %d;\n", layer); cmd += h;

  sprintf(h, "POLYGON "); cmd += h;
  if(radius == 0){
    transform(-dx/2,        -dy/2,          angle, cx, cy);   sprintf(h, "(%5.3f %5.3f) ", u2mm(x), u2mm(y)); cmd += h;
    transform(-dx/2,        dy/2,           angle, cx, cy);   sprintf(h, "(%5.3f %5.3f) ", u2mm(x), u2mm(y)); cmd += h;
    transform(+dx/2,        dy/2,           angle, cx, cy);   sprintf(h, "(%5.3f %5.3f) ", u2mm(x), u2mm(y)); cmd += h;
    transform(+dx/2,        -dy/2,          angle, cx, cy);   sprintf(h, "(%5.3f %5.3f) ", u2mm(x), u2mm(y)); cmd += h;
    transform(-dx/2,        -dy/2,          angle, cx, cy);   sprintf(h, "(%5.3f %5.3f) ", u2mm(x), u2mm(y)); cmd += h;
  } else if(dx==dy && dx/2 == radius){
    transform(-dx/2,        0,              angle, cx, cy);   sprintf(h, "(%5.3f %5.3f) ", u2mm(x), u2mm(y)); cmd += h;
    transform(0,            dy/2,           angle, cx, cy);   sprintf(h, "-90 (%5.3f %5.3f) ", u2mm(x), u2mm(y)); cmd += h;
    transform(+dx/2,        0,              angle, cx, cy);   sprintf(h, "-90 (%5.3f %5.3f) ", u2mm(x), u2mm(y)); cmd += h;
    transform(0,            -dy/2,          angle, cx, cy);   sprintf(h, "-90 (%5.3f %5.3f) ", u2mm(x), u2mm(y)); cmd += h;
    transform(-dx/2,        -dy/2+radius,   angle, cx, cy);   sprintf(h, "-90 (%5.3f %5.3f) ", u2mm(x), u2mm(y)); cmd += h; 
  } else if(dx/2 == radius){
    transform(-dx/2,        -dy/2+radius,   angle, cx, cy);   sprintf(h, "(%5.3f %5.3f) ", u2mm(x), u2mm(y)); cmd += h;
    transform(-dx/2,        dy/2-radius,    angle, cx, cy);   sprintf(h, "(%5.3f %5.3f) ", u2mm(x), u2mm(y)); cmd += h;
    transform(0,            dy/2,           angle, cx, cy);   sprintf(h, "-90 (%5.3f %5.3f) ", u2mm(x), u2mm(y)); cmd += h;
    transform(+dx/2,        dy/2-radius,    angle, cx, cy);   sprintf(h, "-90 (%5.3f %5.3f) ", u2mm(x), u2mm(y)); cmd += h;
    transform(+dx/2,        -dy/2+radius,   angle, cx, cy);   sprintf(h, "(%5.3f %5.3f) ", u2mm(x), u2mm(y)); cmd += h;
    transform(0,            -dy/2,          angle, cx, cy);   sprintf(h, "-90 (%5.3f %5.3f) ", u2mm(x), u2mm(y)); cmd += h;
    transform(-dx/2,        -dy/2+radius,   angle, cx, cy);   sprintf(h, "-90 (%5.3f %5.3f) ", u2mm(x), u2mm(y)); cmd += h;    
  } else if(dy/2 == radius){
    transform(-dx/2,        0,              angle, cx, cy);   sprintf(h, "(%5.3f %5.3f) ", u2mm(x), u2mm(y)); cmd += h;
    transform(-dx/2+radius, dy/2,           angle, cx, cy);   sprintf(h, "-90 (%5.3f %5.3f) ", u2mm(x), u2mm(y)); cmd += h;
    transform(+dx/2-radius, dy/2,           angle, cx, cy);   sprintf(h, "(%5.3f %5.3f) ", u2mm(x), u2mm(y)); cmd += h;
    transform(+dx/2,        0,              angle, cx, cy);   sprintf(h, "-90 (%5.3f %5.3f) ", u2mm(x), u2mm(y)); cmd += h;
    transform(+dx/2-radius, -dy/2,          angle, cx, cy);   sprintf(h, "-90 (%5.3f %5.3f) ", u2mm(x), u2mm(y)); cmd += h;
    transform(-dx/2+radius, -dy/2,          angle, cx, cy);   sprintf(h, "(%5.3f %5.3f) ", u2mm(x), u2mm(y)); cmd += h;
    transform(-dx/2,        0,              angle, cx, cy);   sprintf(h, "-90 (%5.3f %5.3f) ", u2mm(x), u2mm(y)); cmd += h;       
  } else {
    transform(-dx/2,        -dy/2+radius,   angle, cx, cy);   sprintf(h, "(%5.3f %5.3f) ", u2mm(x), u2mm(y)); cmd += h;
    transform(-dx/2,        dy/2-radius,    angle, cx, cy);   sprintf(h, "(%5.3f %5.3f) ", u2mm(x), u2mm(y)); cmd += h;
    transform(-dx/2+radius, dy/2,           angle, cx, cy);   sprintf(h, "-90 (%5.3f %5.3f) ", u2mm(x), u2mm(y)); cmd += h;
    transform(+dx/2-radius, dy/2,           angle, cx, cy);   sprintf(h, "(%5.3f %5.3f) ", u2mm(x), u2mm(y)); cmd += h;
    transform(+dx/2,        dy/2-radius,    angle, cx, cy);   sprintf(h, "-90 (%5.3f %5.3f) ", u2mm(x), u2mm(y)); cmd += h;
    transform(+dx/2,        -dy/2+radius,   angle, cx, cy);   sprintf(h, "(%5.3f %5.3f) ", u2mm(x), u2mm(y)); cmd += h;
    transform(+dx/2-radius, -dy/2,          angle, cx, cy);   sprintf(h, "-90 (%5.3f %5.3f) ", u2mm(x), u2mm(y)); cmd += h;
    transform(-dx/2+radius, -dy/2,          angle, cx, cy);   sprintf(h, "(%5.3f %5.3f) ", u2mm(x), u2mm(y)); cmd += h;
    transform(-dx/2,        -dy/2+radius,   angle, cx, cy);   sprintf(h, "-90 (%5.3f %5.3f) ", u2mm(x), u2mm(y)); cmd += h;    
  }

  sprintf(h, ";\n"); cmd += h;


  /*
	if(roundness != 100 || (dx != dy))
	{
		sprintf(h, "RECT R%f (%f %f) (%f %f);", angle, u2mm(rx), u2mm(ry), u2mm(rdx), u2mm(rdy)); cmd += h;
	}
	else	//Simple fix for round fiducials
	{
		sprintf(h, "CIRCLE 0 (%f %f) (%f %f);", u2mm( cx ), u2mm( cy ), u2mm(x+(dx/2)), u2mm(cy)); cmd += h;	
	}
  */
}

void do_hole(UL_HOLE hole) {
	string h = "";
	sprintf(h, "CHANGE LAYER %s;\n", emptyname); cmd += h;
	sprintf(h, "CIRCLE 0 (%5.3f %5.3f) (%5.3f %5.3f);\n", u2mm(hole.x), u2mm(hole.y), u2mm(hole.x + (hole.drill/2)), u2mm(hole.y)); cmd += h;
} 

void do_via(UL_VIA v) {
	create_via(v.x, v.y, v.drill, v.diameter[LAYER_TSTOP], v.diameter[LAYER_BSTOP], v.shape[1], 0.0); //We use Layer one for all via symbols
}

void do_pad(UL_PAD p) {
	if(p) {
		create_via(p.x, p.y, p.drill, p.diameter[LAYER_TSTOP], p.diameter[LAYER_BSTOP], p.shape[1], p.angle);
	}
}

int silkscreens_already_exist(UL_BOARD B) {
  int found = 0;
  B.layers(L) if(L.number == emptynum || L.number == dimensionnum) found = 1;
  return found;
}

void save_visible_layers(UL_BOARD B) {
  int i = 0;
  B.layers(L) if(L.visible) saved_visible_layers[i++] = L.name;
  saved_visible_layers[i] = "";
}

void restore_visible_layers(UL_BOARD B) {
  int i;
  cmd += "display none";
  for(i = 0; saved_visible_layers[i] != ""; i++) {
    h = "";sprintf(h, " %s", saved_visible_layers[i]);cmd += h;
  }
  cmd += ";\n";
}

void clear_silkscreen_layers(UL_BOARD B) {
  real x1 = u2mm(B.area.x1);
  real x2 = u2mm(B.area.x2);
  real y1 = u2mm(B.area.y1);
  real y2 = u2mm(B.area.y2);
  save_visible_layers(B);
  h = "";sprintf(h, "display ?? none %s %s %s;\n", dimensionname, backgroundname, emptyname);cmd += h;
  h = "";sprintf(h, "group (%5.3f %5.3f) (%5.3f %5.3f) (%5.3f %5.3f) "
                    "(%5.3f %5.3f) (%5.3f %5.3f);\n", x1, y1, x2, y1,
                    x2, y2, x1, y2, x1, y1);cmd += h;
  cmd += "delete (> 0 0);\n";
  restore_visible_layers(B);
}

void hide_source_layers() {
  cmd += "display";
  if(copy_tdimension) cmd += " -Dimension";
  cmd += ";\n";
}

// As well as setting destlayer, also returns 0 if the specified source
// layer is not one of the ones we were asked to copy. If the source is
// Dimension, sets a destlayer of tsilknum, and you then have to do the copy
// a second time with the destlayer set to bsilknum because Dimension gets
// copied to both silk screens.

void run_script() {
	string working_dir = "";
	
	board(B) {
		working_dir = filedir(B.name);	
	}
	string scr = working_dir + "tmp.scr";

	output(scr, "w") {
		printf("%s", cmd);
	}
	exit(";SCRIPT '" + scr + "';");	
}

void save_grid(UL_BOARD B) {
  saved_grid_unit = B.grid.unit;
}

void restore_grid() {
  switch(saved_grid_unit) {
    case GRID_UNIT_MIC:
      cmd += "grid mic;\n";
      break;
    case GRID_UNIT_MM:
      cmd += "grid mm;\n";
      break;
    case GRID_UNIT_INCH:
      cmd += "grid inch;\n";
      break;
    case GRID_UNIT_MIL:
    default:
      cmd += "grid mil;\n";
      break;
  }
}

void swopPlaces(int index1, int index2){
  real tmp;

  tmp       = wX1[index1];
  wX1[index1]  = wX1[index2];
  wX1[index2]  = tmp;

  tmp       = wY1[index1];
  wY1[index1]  = wY1[index2];
  wY1[index2]  = tmp;

  tmp       = wX2[index1];
  wX2[index1]  = wX2[index2];
  wX2[index2]  = tmp;

  tmp       = wY2[index1];
  wY2[index1]  = wY2[index2];
  wY2[index2]  = tmp;

  tmp       = wRad[index1];
  wRad[index1] = wRad[index2];
  wRad[index2] = tmp;

  tmp       = wWid[index1];
  wWid[index1] = wWid[index2];
  wWid[index2] = tmp;
}

void reverseDirection(int index){
  wX2[index] = wX2[index] + wX1[index];
  wX1[index] = wX2[index] - wX1[index];
  wX2[index] = wX2[index] - wX1[index];

  wY2[index] = wY2[index] + wY1[index];
  wY1[index] = wY2[index] - wY1[index];
  wY2[index] = wY2[index] - wY1[index];

  wRad[index]*=-1;
}

if(board) {
  board(B) {

    save_grid(B);


    if(minwidth && maxwidth && minwidth > maxwidth) {
      dlgMessageBox(":Minimum width must be less than maximum width.");
      exit(1);
    }

    if(silkscreens_already_exist(B) && delete_old) clearsilks = 1;

    header();

    if(clearsilks) clear_silkscreen_layers(B);
    if(hide_sources) hide_source_layers();

    B.elements(E) {
        destlayer = dimensionnum;
        do_element(E, LAYER_DIMENSION);
        destlayer = backgroundnum;
        do_element(E, LAYER_DIMENSION);
    }
    B.wires(W) {
    	if(W.layer == LAYER_DIMENSION) {
        destlayer = dimensionnum;
        do_wire(W, W.layer);
        destlayer = backgroundnum;
        do_wire(W, W.layer);
    	}
    }
    B.circles(C) {
    	if(C.layer == LAYER_DIMENSION) {
        destlayer = dimensionnum;
        do_circle(C);
        destlayer = backgroundnum;
        do_circle(C);
    	}
    }
    B.rectangles(R) {
    	if(R.layer == LAYER_DIMENSION) {
        destlayer = dimensionnum;
        do_rectangle(R);
        destlayer = backgroundnum;
        do_rectangle(R);
    	}
    }
    B.polygons(P) {
    	if(P.layer == LAYER_DIMENSION) {
        destlayer = dimensionnum;
        do_polygon(P);    
        destlayer = backgroundnum;
        do_polygon(P);    
    	}
    }
  	B.holes(H) {
  		do_hole(H);
  	}
  	B.signals(S) {
  		S.vias(V) {
  			do_via(V);
  		}
  	}

  	B.elements(E)  {
  		E.package.holes(H) {
  			do_hole(H);
  		}
  		E.package.contacts(C) {
  			do_pad(C.pad);
  		}
  	}
  }

  if(EAGLE_VERSION>=9){
    cmd += "display none "+emptyname+" "+backgroundname+";\n";

    int blockStartIndex[];
    int blockEndIndex[];
    real blockLeangth[];
    int i, si=0;

    blockStartIndex[si]=-1;
    for(i=0;i<index;i++){
      if(blockStartIndex[si]==-1){ //new block
        blockStartIndex[si]=i;
        blockLeangth[si]=0;
      }
      else if((wX1[i]==wX2[i-1])&&(wY1[i]==wY2[i-1])){
      }
      else if ((wX2[i]==wX2[i-1])&&(wY2[i]==wY2[i-1])){
        //reversing the direction of the wire so every wire either gos cclockwise or countercclockwise
        reverseDirection(i);
      }
      else{
        for(int j=i+1;j<index;j++){
          if((wX1[j]==wX2[i-1])&&(wY1[j]==wY2[i-1])){
            swopPlaces(i,j);
            break;
          }
          else if((wX2[j]==wX2[i-1])&&(wY2[j]==wY2[i-1])){
            swopPlaces(i,j);

            //reversing the direction of the wire so every wire either gos cclockwise or countercclockwise
            reverseDirection(i);

            break;
          }
        }
      }
      blockEndIndex[si]=i;

      if((wX1[i]==wX2[i])&&(wY1[i]==wY2[i])){
        blockLeangth[si]=2*wRad[i]*PI;
        blockStartIndex[++si]=-1;
      }
      else if(wX1[blockStartIndex[si]]==wX2[i] && wY1[blockStartIndex[si]]==wY2[i]){
        blockLeangth[si] += sqrt(pow((wX2[i]-wX1[i]),2)+pow((wY2[i]-wY1[i]),2));
        blockStartIndex[++si]=-1;
      }
      else{
        blockLeangth[si] += sqrt(pow((wX2[i]-wX1[i]),2)+pow((wY2[i]-wY1[i]),2));
      }
    }

    int longest=0;
    for(i=0;i<si;i++){
      if(blockLeangth[longest]<blockLeangth[i]){
        longest=i;
      }
    }
    //sprintf(h,"s%d e%d",index,si); dlgMessageBox(h);

    for(i=0;i<index;i++){
      if((blockStartIndex[longest]<=i)&&(i<=blockEndIndex[longest])){
        cmd+="CHANGE LAYER "+backgroundname+"; ";
      }
      else {
        cmd+="CHANGE LAYER "+emptyname+"; ";
      }

      if((wX1[i]==wX2[i])&&(wY1[i]==wY2[i])){
        sprintf(cmd, "%s circle 0 (%5.3f %5.3f) (%5.3f %5.3f);\n", cmd,
            u2mm(wX1[i]), u2mm(wY1[i]), 
            u2mm(wX1[i] + wRad[i]), u2mm(wY1[i])
        );
      }
      else{
        sprintf(cmd, "%s wire %5.3f (%5.3f %5.3f) @%+5.3f (%5.3f %5.3f);\n", cmd, 
            calcwidth(wWid[i]),
            u2mm(wX1[i]), u2mm(wY1[i]),
            u2mm(wRad[i]),
            u2mm(wX2[i]), u2mm(wY2[i])
        );

        sprintf(cmd,"%spolygonize (%f %f);\n",cmd ,u2mm(wX1[i]),u2mm(wY1[i]));
      }
    }
  }

  if(disable_undo) cmd += "set undo_log on;\n";
  restore_grid();

  run_script(); // Doesn't return.
} else dlgMessageBox(":Error: this ULP only works on board layouts.");
