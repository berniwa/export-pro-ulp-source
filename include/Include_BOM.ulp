/************************************************************/
/* HTL_Export4_BOM.ulp                                      */
/* - Generiert eine Stückliste nach den FTKL Richtlinien    */
/*   der HTL - Salzburg                                     */
/************************************************************/
/* (c) Copyright 2009, Bernhard Wörndl-Aichriedler          */
/* xDevelop OG - Hardware Developer							*/
/* E-Mail: bwa@berniwa.com (bwa@xdevelop.at)                */
/* Homepage: www.berniwa.com (www.xdevelop.at)              */
/************************************************************/
/* Die Verwendung, das Kopieren bzw. die Weiterverbreitung  */
/* dieses ULP sind nur nach ausdrücklicher Erlaubnis des    */
/* Autors gestattet! 										*/
/************************************************************/
/* Letzte Änderung am 28.01.2009                            */
/* Version 1.0 (in Export 3.3)                              */
/************************************************************/
/* Letzte Änderung am 10.12.2009                            */
/* Version 2.0 (in Export 4.0)                              */
/************************************************************/

#include "Include_BomConfig.ulp"
#include "Include_String.ulp"
#include "Include_Si.ulp"
#include "Include_BomCategory.ulp"

int 	bomDisplayPackageType 		= 0;
int 	bomShortPartNames 			= 0;
int 	bomExportXls 				= 0;
int 	bomExportXlsx 				= 0;
int 	bomExportCsv 				= 0;
int 	bomExportDbase3 			= 0;
int 	bomExportFarnellBom 		= 0;
int 	bomExportPnpBom				= 0;
real	bomExportFarnellMultiplier	= 1.0;
int 	bomExportPdf 				= 0;
real 	bomPdfoffsetX 				= 0;
real 	bomPdfoffsetY 				= 0;
real 	bomPdfWidth					= 180;

int	bomInfoCount = 0;

/* Data field definitions */
int		bomInfoPartId[];
int		bomInfoPartCount[];
string	bomInfoName[];
string	bomInfoParts[];
string	bomInfoValue[];
int		bomInfoHasParsedValue[];
real	bomInfoParsedValue[];
string	bomInfoPackage[];
string	bomInfoDevice[];
string	bomInfoDescription[]; 
string	bomAttributeDistributor[];
string	bomAttributeOrderNo[];
string	bomAttributeManufacturer[];
string 	bomAttributePartNo[];
string	bomAttributeReferenceNo[];
string	bomAttributeReserved1[];
string	bomAttributeReserved2[];
string	bomAttributePrice[];
string	bomAttributePrices[];
string	bomAttributeAvailableQuantity[];
string	bomAttributePartsPerPackage[];
string	bomAttributeMinimumQuantity[];
string	bomAttributeQuantityMultiplier[];
string	bomAttributeDatasheet[];
string	bomAttributePopulate[];
string	bomAttributeNote[];
int		bomAttributeCategory[];

int		bomOutputCount[];
string	bomOutputName[];
string	bomOutputParts[];
string	bomOutputNote[];
string	bomOutputGP1[];
string	bomOutputGP2[];
string	bomOutputGP3[];
string	bomOutputGP4[];

#include "Include_BomExportDbase.ulp"
#include "Include_BomExportXml.ulp"
#include "Include_BomExportFarnell.ulp"
#include "Include_BomExportCsv.ulp"
#include "Include_BomExportPnp.ulp"
#include "Include_BomExportPdf.ulp"

string bomValuesGet(int pid, string name) {
	if(name == "PACKAGE")
	{
		return bomInfoPackage[pid];
	}
	else if(name == "DEVICE")
	{
		return bomInfoDevice[pid];
	}
	else if(name == "DESCRIPTION")
	{
		return bomInfoDescription[pid];
	}
	else if(name == "PARTS")
	{
		return bomInfoParts[pid];
	}
	else if(name == "VALUE")
	{
		return bomInfoValue[pid];
	}
	else if(name == "PARSED_VALUE")
	{
		string tmp;
		sprintf(tmp, "%e",bomInfoParsedValue[pid]);
		return tmp;
	}
	else if(name == "GRID")
	{
		string tmp;
		if((tmp = stringParameterValue("grid", bomInfoDescription[pid])) != "")
		{
			tmp = stringReplace(tmp, "mm", "");
			return "RM" + tmp;
		}
		return "";
	}
	else if(name == "PSIZE")
	{
		string tmp;

		if(stringParameterPresent("chip", bomInfoDescription[pid]))
		{
			if(bomDisplayPackageType)
			{
				return "SMD " + strsub(bomInfoPackage[pid], 1);
			}
			else
			{
				return strsub(bomInfoPackage[pid], 1);
			}
		}
		else if(stringParameterPresent("MELF", bomInfoDescription[pid]))
		{
			if(bomDisplayPackageType)
			{
				return "MELF " + strsub(bomInfoPackage[pid], 1);
			}
			else
			{
				return strsub(bomInfoPackage[pid], 1);
			}
		}
		else if(stringParameterPresent("outline", bomInfoDescription[pid]))
		{
			return stringParameterValue("outline", bomInfoDescription[pid]);
		}
		else if(stringParameterPresent("diameter", bomInfoDescription[pid]))
		{
			return stringParameterValue("diameter", bomInfoDescription[pid]) + " radial";
		}
		else if(stringParameterPresent("type", bomInfoDescription[pid]))
		{
			return stringParameterValue("type", bomInfoDescription[pid]);
		}
		else
		{
			return bomInfoPackage[pid];
		}
		
	}
	else
	{
		return "";
	}
}

string bomWildcardReplaceWithValues(int pid, string wildcarded) {
	while(strstr(wildcarded, BOM_WILDCARD_STR) != -1)
	{
		string wildcard = stringWildcardGetNext(wildcarded);
		wildcarded = stringWildcardReplace(wildcarded, wildcard, bomValuesGet(pid, wildcard));
	}
	return wildcarded;
}

int bomPartPresent(string value, string dev, string pack, string desc, string distributor, string orderNo, string manufacturer, string partNo, string referenceNo, string reserved1, string reserved2, string populate) {
	for(int i = 0; i < bomInfoCount; i++)
	{
		if(	distributor != "" && orderNo != "" &&
			bomAttributeDistributor[i] == distributor && 
			bomAttributeOrderNo[i] == orderNo && 
			bomAttributeManufacturer[i] == manufacturer && 
			bomAttributePartNo[i] == partNo && 
			bomAttributeReferenceNo[i] == referenceNo &&
			bomAttributeReserved1[i] == reserved1 && 
			bomAttributeReserved2[i] == reserved2 &&
			bomAttributePopulate[i] == populate
		)
		{
			if(value != bomInfoValue[i])
			{
				bomInfoValue[i] = "";
			}
			return i;
		}

		if(	bomInfoValue[i] == value && 
			bomInfoDevice[i] == dev && 
			bomInfoPackage[i] == pack && 
			bomInfoDescription[i] == desc &&
			bomAttributePopulate[i] == populate
		)
		{
			return i;
		}
	}
	return -1;
}

void bomPartsLoadPart(UL_PART P, string prefix) {
	if (P.device.package)  {
		int pdevice = 0;

		string distributor 			= P.attribute["DISTRIBUTOR"];
		string orderNo 				= P.attribute["ORDER_NO"];
		string manufacturer 		= P.attribute["MANUFACTURER"];
		string partNo 				= P.attribute["PART_NO"];
		string referenceNo 			= P.attribute["REFERENCE_NO"];
		string reserved1 			= P.attribute["RESERVED1"];
		string reserved2 			= P.attribute["RESERVED2"];
		string price 				= P.attribute["PRICE"];
		string prices 				= P.attribute["PRICES"];
		string availableQuantity 	= P.attribute["AVAILABLE_QUANTITY"];
		string partsPerPackage		= P.attribute["PARTS_PER_PACKAGE"];
		string minimumQuantity		= P.attribute["MINIMUM_QUANTITY"];
		string quantityMultiplier	= P.attribute["QUANTITY_MULTIPLIER"];
		string datasheet 			= P.attribute["DATASHEET"];
		string populate 			= P.attribute["POPULATE"];
		string note 				= P.attribute["NOTE"];
		int    category				= BOM_PART_UNRECOGNISED;

		if(P.attribute["CATEGORY"]) {
			category				= strtol(P.attribute["CATEGORY"]);
		} 

		//Resolve category
		int 	categoryIndex 		= 0;
		for(int j = 0; j < BOM_DATA_COUNT; j++) {
			if(BOM_DATA_PART_ID[j] == category) {
				categoryIndex = j; 
				break;
			}
		}

		if((pdevice = bomPartPresent(
				P.value,P.device.name,P.device.package.name,
				P.device.package.description,distributor, 
				orderNo, manufacturer, partNo, referenceNo, 
				reserved1, reserved2, populate)
				) != -1) {
			bomInfoParts[pdevice] += "," + prefix + P.name;
			bomInfoPartCount[pdevice]++;				
		}
		else if(BOM_DATA_HIDE_IN_BOM[categoryIndex]) {
			//Ignore the part totally!
		}
		else {
			bomInfoParts[bomInfoCount] 						= prefix + P.name;
			bomInfoValue[bomInfoCount] 						= P.value;
			bomInfoDevice[bomInfoCount] 					= P.device.name;
			bomInfoPackage[bomInfoCount] 					= P.device.package.name;
			bomInfoDescription[bomInfoCount] 				= P.device.package.description;
			bomAttributeDistributor[bomInfoCount] 			= distributor;
			bomAttributeOrderNo[bomInfoCount] 				= orderNo;
			bomAttributeManufacturer[bomInfoCount] 			= manufacturer;
			bomAttributePartNo[bomInfoCount] 				= partNo;
			bomAttributeReferenceNo[bomInfoCount] 			= referenceNo;
			bomAttributeReserved1[bomInfoCount] 			= reserved1;
			bomAttributeReserved2[bomInfoCount] 			= reserved2;
			bomAttributePrice[bomInfoCount] 				= price;
			bomAttributePrices[bomInfoCount] 				= prices;
			bomAttributeAvailableQuantity[bomInfoCount] 	= availableQuantity;
			bomAttributePartsPerPackage[bomInfoCount] 		= partsPerPackage;
			bomAttributeMinimumQuantity[bomInfoCount]		= minimumQuantity;
			bomAttributeQuantityMultiplier[bomInfoCount] 	= quantityMultiplier;
			bomAttributeDatasheet[bomInfoCount] 			= datasheet;
			bomAttributePopulate[bomInfoCount] 				= populate;
			bomAttributeCategory[bomInfoCount] 				= category;
			bomAttributeNote[bomInfoCount]					= note;


			bomInfoPartCount[bomInfoCount] = 1;
			bomInfoCount++;
		}
	}
}

void bomPartsLoad() {
	project.schematic(SCH){
		SCH.parts(P){
			bomPartsLoadPart(P, "");
      	}
      	SCH.sheets(S) {
			S.moduleinsts(M) {
				M.module.parts(P){
					bomPartsLoadPart(P, M.name + ":");
				}
			}
		}
	}
}

void bomPartsCategorize() {
	for(int i = 0; i < bomInfoCount; i++)
	{
		int k = bomAttributeCategory[i];

		if(k == BOM_PART_UNRECOGNISED)
		{
			k = bomCategorize(bomInfoParts[i], bomInfoValue[i], bomInfoDevice[i], 
				bomInfoPackage[i], bomInfoDescription[i]
			);			
		}

		//Resolve category
		for(int j = 0; j < BOM_DATA_COUNT; j++)
		{
			if(BOM_DATA_PART_ID[j] == k){k = j; break;}
		}

		if(BOM_DATA_PARSE_VALUE[k])
		{
			bomInfoHasParsedValue[i] = 1;
			bomInfoParsedValue[i] = siParseValue(bomInfoValue[i]);
		}
		bomInfoPartId[i] = BOM_DATA_PART_ID[k];
		bomOutputCount[i] = bomInfoPartCount[i];
		bomOutputName[i] = BOM_DATA_NAME[k] + " " + bomInfoValue[i];
		bomOutputParts[i] = bomInfoParts[i];
		bomOutputNote[i] = bomWildcardReplaceWithValues(i, BOM_DATA_NOTE[k]);
		bomOutputGP1[i] = bomWildcardReplaceWithValues(i, bomOutputGP1[k]);
		bomOutputGP2[i] = bomWildcardReplaceWithValues(i, bomOutputGP2[k]);
		bomOutputGP3[i] = bomWildcardReplaceWithValues(i, bomOutputGP3[k]);
		bomOutputGP4[i] = bomWildcardReplaceWithValues(i, bomOutputGP4[k]);
	}
}

void bomPartSwitch(int pid1, int pid2) {
	string	tmpOutputName					= bomOutputName[pid1];
	string	tmpOutputParts					= bomOutputParts[pid1];
	string	tmpOutputNote					= bomOutputNote[pid1];
	string	tmpOutputGP1					= bomOutputGP1[pid1];
	string	tmpOutputGP2					= bomOutputGP2[pid1];
	string	tmpOutputGP3					= bomOutputGP3[pid1];
	string	tmpOutputGP4					= bomOutputGP4[pid1];
	int		tmpInfoPartId					= bomInfoPartId[pid1];
	int		tmpInfoPartCount				= bomInfoPartCount[pid1];
	string	tmpInfoName						= bomInfoName[pid1];
	string	tmpInfoParts					= bomInfoParts[pid1];
	string	tmpInfoValue					= bomInfoValue[pid1];
	int		tmpInfoHasParsedValue 			= bomInfoHasParsedValue[pid1];
	real	tmpInfoParsedValue				= bomInfoParsedValue[pid1];
	string	tmpInfoPackage					= bomInfoPackage[pid1];
	string	tmpInfoDevice					= bomInfoDevice[pid1];
	string	tmpInfoDescription				= bomInfoDescription[pid1]; 
	string	tmpAttributeDistributor			= bomAttributeDistributor[pid1];
 	string	tmpAttributeOrderNo				= bomAttributeOrderNo[pid1];
 	string	tmpAttributeManufacturer		= bomAttributeManufacturer[pid1];
 	string	tmpAttributePartNo				= bomAttributePartNo[pid1];
 	string	tmpAttributeReferenceNo			= bomAttributeReferenceNo[pid1];
	string 	tmpAttributeReserved1			= bomAttributeReserved1[pid1];
	string 	tmpAttributeReserved2			= bomAttributeReserved2[pid1];
	string 	tmpAttributePrice				= bomAttributePrice[pid1];
	string 	tmpAttributePrices				= bomAttributePrices[pid1];
	string 	tmpAttributeAvailableQuantity	= bomAttributeAvailableQuantity[pid1];
	string 	tmpAttributePartsPerPackage		= bomAttributePartsPerPackage[pid1];
	string 	tmpAttributeMinimumQuantity		= bomAttributeMinimumQuantity[pid1];
	string 	tmpAttributeQuantityMultiplier	= bomAttributeQuantityMultiplier[pid1];
	string 	tmpAttributeDatasheet			= bomAttributeDatasheet[pid1];
	string 	tmpAttributePopulate			= bomAttributePopulate[pid1];
	string 	tmpAttributeNote				= bomAttributeNote[pid1];


	
	bomOutputName[pid1]						= bomOutputName[pid2];
	bomOutputParts[pid1]					= bomOutputParts[pid2];
	bomOutputNote[pid1]						= bomOutputNote[pid2];
	bomOutputGP1[pid1]						= bomOutputGP1[pid2];
	bomOutputGP2[pid1]						= bomOutputGP2[pid2];
	bomOutputGP3[pid1]						= bomOutputGP3[pid2];
	bomOutputGP4[pid1]						= bomOutputGP4[pid2];
	bomInfoPartId[pid1]						= bomInfoPartId[pid2];
	bomInfoPartCount[pid1]					= bomInfoPartCount[pid2];
	bomInfoName[pid1]						= bomInfoName[pid2];
	bomInfoParts[pid1]						= bomInfoParts[pid2];
	bomInfoValue[pid1]						= bomInfoValue[pid2];
	bomInfoHasParsedValue[pid1]				= bomInfoHasParsedValue[pid2];
	bomInfoParsedValue[pid1]				= bomInfoParsedValue[pid2];
	bomInfoPackage[pid1]					= bomInfoPackage[pid2];
	bomInfoDevice[pid1]						= bomInfoDevice[pid2];
	bomInfoDescription[pid1]				= bomInfoDescription[pid2]; 
	bomAttributeDistributor[pid1] 			= bomAttributeDistributor[pid2];
	bomAttributeOrderNo[pid1] 				= bomAttributeOrderNo[pid2];
	bomAttributeManufacturer[pid1] 			= bomAttributeManufacturer[pid2];
	bomAttributePartNo[pid1] 				= bomAttributePartNo[pid2];
	bomAttributeReferenceNo[pid1] 			= bomAttributeReferenceNo[pid2];	
	bomAttributeReserved1[pid1]				= bomAttributeReserved1[pid2];
	bomAttributeReserved2[pid1]				= bomAttributeReserved2[pid2];
	bomAttributePrice[pid1]					= bomAttributePrice[pid2];
	bomAttributePrices[pid1]				= bomAttributePrices[pid2];
	bomAttributeAvailableQuantity[pid1]		= bomAttributeAvailableQuantity[pid2];
	bomAttributePartsPerPackage[pid1]		= bomAttributePartsPerPackage[pid2];
	bomAttributeMinimumQuantity[pid1]		= bomAttributeMinimumQuantity[pid2];
	bomAttributeQuantityMultiplier[pid1]	= bomAttributeQuantityMultiplier[pid2];
	bomAttributeDatasheet[pid1]				= bomAttributeDatasheet[pid2];
	bomAttributePopulate[pid1]				= bomAttributePopulate[pid2];
	bomAttributeNote[pid1]					= bomAttributeNote[pid2];


	bomOutputName[pid2]						= tmpOutputName;
	bomOutputParts[pid2]					= tmpOutputParts;
	bomOutputNote[pid2]						= tmpOutputNote;
	bomOutputGP1[pid2]						= tmpOutputGP1;
	bomOutputGP2[pid2]						= tmpOutputGP2;
	bomOutputGP3[pid2]						= tmpOutputGP3;
	bomOutputGP4[pid2]						= tmpOutputGP4;
	bomInfoPartId[pid2]						= tmpInfoPartId;
	bomInfoPartCount[pid2]					= tmpInfoPartCount;
	bomInfoName[pid2]						= tmpInfoName;
	bomInfoParts[pid2]						= tmpInfoParts;
	bomInfoValue[pid2]						= tmpInfoValue;
	bomInfoHasParsedValue[pid2]				= tmpInfoHasParsedValue;
	bomInfoParsedValue[pid2]				= tmpInfoParsedValue;
	bomInfoPackage[pid2]					= tmpInfoPackage;
	bomInfoDevice[pid2]						= tmpInfoDevice;
	bomInfoDescription[pid2]				= tmpInfoDescription; 
	bomAttributeDistributor[pid2] 			= tmpAttributeDistributor;
	bomAttributeOrderNo[pid2] 				= tmpAttributeOrderNo;
	bomAttributeManufacturer[pid2] 			= tmpAttributeManufacturer;
	bomAttributePartNo[pid2] 				= tmpAttributePartNo;
	bomAttributeReferenceNo[pid2] 			= tmpAttributeReferenceNo;	
	bomAttributeReserved1[pid2]				= tmpAttributeReserved1;
	bomAttributeReserved2[pid2]				= tmpAttributeReserved2;
	bomAttributePrice[pid2]					= tmpAttributePrice;
	bomAttributePrices[pid2]				= tmpAttributePrices;
	bomAttributeAvailableQuantity[pid2]		= tmpAttributeAvailableQuantity;
	bomAttributePartsPerPackage[pid2]		= tmpAttributePartsPerPackage;
	bomAttributeMinimumQuantity[pid2]		= tmpAttributeMinimumQuantity;
	bomAttributeQuantityMultiplier[pid2]	= tmpAttributeQuantityMultiplier;
	bomAttributeDatasheet[pid2]				= tmpAttributeDatasheet;	
	bomAttributePopulate[pid2]				= tmpAttributePopulate;	
	bomAttributeNote[pid2]					= tmpAttributeNote;	
}

int bomPartSortRoutine(int pid1, int pid2) {
	if(bomInfoPartId[pid1] == bomInfoPartId[pid2]) {
		if(bomInfoHasParsedValue[pid1]) {	//Values computed 
			if(bomInfoParsedValue[pid1] > bomInfoParsedValue[pid2]) {
				return 1;
			}
			else if(bomInfoParsedValue[pid1] == bomInfoParsedValue[pid2]) {
				if(bomOutputNote[pid1] > bomOutputNote[pid2]) {
					return 1;
				}
			}
		}
		else {
			int compare = stringCompare(bomInfoValue[pid1], bomInfoValue[pid2]);

			if(compare == 0) {
				if(bomOutputNote[pid1] > bomOutputNote[pid2]) {
					return 1;
				}
			}
			else if(compare < 0) {
				return 1;
			}
		}

	}
	else if(bomInfoPartId[pid1] > bomInfoPartId[pid2]) {
		return 1;
	}
	return 0;
}

void bomPartsSort() {
	int ready = 0;

	while(!ready) {
		ready = 1;

		for(int i = 0; i < bomInfoCount-1; i++) {		
			if(bomPartSortRoutine(i, i+1)) {
				ready = 0;
				bomPartSwitch(i, i+1);
			}
		}

	}	
}

void bomShortenNames() {
	for(int i = 0; i < bomInfoCount-1; i++) {
		numeric string names[];
		int count = strsplit(names, bomOutputParts[i], ',');
		sort(count, names);
 
		int start_id = -1, last_id = -1;
		string snames = "";

		for(int k = 0; k < count; k++) {
			if(snames == "") {
				snames = strsub(names[k], 0, 1);
			}
			
			string sid = strsub(names[k], 1);
			int id = strtol(sid);
			
			if(start_id == -1) {
				start_id = id;
				last_id = id;
			}
			else if(last_id + 1 == id) {
				last_id = id;
			}
			else {
				if(strlen(snames) > 1) {
					snames += ",";
				}
				if(last_id == start_id) {
					string tmp = "";
					sprintf(tmp, "%d", start_id);
					snames += tmp;
				}
				else {	
					string tmp = "";
					sprintf(tmp, "%d-%d", start_id, last_id);
					snames += tmp;				
				}
				
				start_id = id;
				last_id = id;
			}
		}

		
		if(strlen(snames) > 1) {
			snames += ",";
		}
		if(last_id == start_id) {
			string tmp = "";
			sprintf(tmp, "%d", start_id);
			snames += tmp;
		}
		else {	
			string tmp = "";
			sprintf(tmp, "%d-%d", start_id, last_id);
			snames += tmp;				
		}


		bomOutputParts[i] = snames;
	}	
}

string bname;

project.schematic(S) {
	bname = S.name;
}


string bomGetFilename(string ends_with) {
	return filesetext(bname,ends_with);
}


void bomProcess() {
	string ofilename = bomGetFilename("");

	if(argc > 1) {
		ofilename = argv[1];	
	}
	for(int i = 2; i < argc; i++) {
		if(argv[i] == "-xls") {
			bomExportXls = 1;
		}
		else if(argv[i] == "-xlsx") {
			bomExportXlsx = 1;
		}
		else if(argv[i] == "-csv") {
			bomExportCsv = 1;
		}
		else if(argv[i] == "-dbase3") {
			bomExportDbase3 = 1;
		}
		else if(argv[i] == "-farnell") {
			bomExportFarnellBom = 1;
		}
		else if(argv[i] == "-pnp") {
			bomExportPnpBom	= 1;
		}
		else if(argv[i] == "-multiplier") {
			if(i + 1 < argc) {
				i++;
				bomExportFarnellMultiplier = strtod(argv[i]);
			}
		}

		else if(argv[i] == "-short_names") {
			bomShortPartNames = 1;
		}
		else if(argv[i] == "-display_package_type") {
			bomDisplayPackageType = 1;
		}
		else if(argv[i] == "-pdf") {
			bomExportPdf = 1;
			if(i + 3 < argc) {
				i++;
				bomPdfoffsetX = strtod(argv[i]);
				i++;
				bomPdfoffsetY = strtod(argv[i]);
				i++;
				bomPdfWidth = strtod(argv[i]);
			}
		}
	}	

	bomPartsLoad();
	bomPartsCategorize();
	bomPartsSort();
	
	if(bomShortPartNames) {
		bomShortenNames();
	}
	if(bomExportXlsx) {
		bomOutputXslFile(ofilename + ".xlsx"); //Office 2007 - written XML style - openable with Office 2003 and up and OO 3.0 and up
	}
	if(bomExportXls) {
		bomOutputXslFile(ofilename + ".xls");  //Office 2003 and 2010 - for all that say - "Woah I don't have Office 2007" - like me =) - but it's the same file as the xlsx
	}
	if(bomExportCsv) {
		bomOutputCsvFile(ofilename + ".csv");  //Good old CSV may be opened with almost everything out there =)
	}
	if(bomExportDbase3) {
		bomOutputDatabaseFile(ofilename + ".dbf"); //DBASE File
	}
	if(bomExportFarnellBom) {
		bomOutputFarnellBom(ofilename + "-farnell.txt", bomExportFarnellMultiplier); //Farnell BOM
	}
	if(bomExportPnpBom) {
		bomOutputPnpFile(ofilename + "-bom.csv");	//Eurocircuits BOM
	}
	if(bomExportPdf) {
		bomOutputPdfFile(bomPdfoffsetX, bomPdfoffsetY, bomPdfWidth);	//PDF BOM
	}
}

bomProcess();
