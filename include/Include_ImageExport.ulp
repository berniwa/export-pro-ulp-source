/************************************************************/
/* HTLExportPro_ImageExport.ulp                             */
/* Exports images of what the PCB will look like            */
/************************************************************/
/* (c) Copyright 2011, Bernhard Wörndl-Aichriedler          */
/* E-Mail: bwa@berniwa.com                                  */
/* Homepage: www.berniwa.com                                */
/************************************************************/
/* Letzte Änderung am 18.02.2011                            */
/* Version 1                                                */
/************************************************************/

#include "Include_FastExecute.ulp";
#include "Include_Misc.ulp";
#include "Include_String.ulp";


int ram = 2147483647;	//in byte
int bytePerPixel = 4;	//R,G,B,Alpha

string getFilename(string basename, string ends_with)
{
	return filesetext(basename,ends_with);
}


string updateFrameInformation(string drawing){
	string name = "";
	string attributes[];
	string attribute;

	board(B) {
		B.elements(E) {
			if(stringCompare(E.package.name, "FRAME") == 0){
				name = E.name;
				int i=0;
				E.attributes(A) {
					attributes[i]=A.name;
					i++;
				}
				attribute = strjoin(attributes,';');
			}
		}
	}

	string cmd = "";
	if(name != "") {

		cmd += "CHANGE DISPLAY OFF;\n";
	 	
	 	if(strstr(attribute,"DRAWING")!=-1) {
			cmd += "ATTRIBUTE " + name + " DRAWING DELETE;\n";
		}

	 	sprintf(cmd, "%sATTRIBUTE %s DRAWING \'%s\';\n", cmd, name, stringTrim(drawing));

	 	if(EAGLE_VERSION>=9){
	 		cmd += "REPOSITION " + name + ";\n";
	 	}
	 }

	return cmd;
}

void exportImages(int imgExport, int pdfExport, int exportBot, string botImage, string botPdf, int exportTop, string topImage, string topPdf, int resolution, int crop, int mirror, string colorPcb, string colorCopper, string colorSilkscreen, string colorPlating, string tsilcLayers, string bsilcLayers, int format, int frame) {
	string cmd = "";

	string bname = "";
	real height, width;
	board(B)
	{
		bname = B.name;

		height = u2inch(B.area.y2-B.area.y1);
		width = u2inch(B.area.x2-B.area.x1);

	}
	string versionLayer="";

	if(EAGLE_VERSION>=9){
		cmd += "SET PALETTE WHITE;\n";
		cmd += "SET COLOR_LAYER 123 20;\n";
		cmd += "SET COLOR_LAYER 124 22;\n";
		cmd += "SET COLOR_LAYER 127 8;\n";
		cmd += "SET PALETTE 22 " + colorPcb + ";\n";
		cmd += "SET Option.LayerSequence 124;\n";
		versionLayer= "123 124 127";
	}
	else{
		cmd += "SET PALETTE COLORED;\n";
		cmd += "SET PALETTE 0 " + colorPcb + ";\n";
		cmd += "SET Option.LayerSequence 20;\n";
		versionLayer= "20 123";
	}

	cmd += "SET COLOR_LAYER 1 16;\n";
	cmd += "SET COLOR_LAYER 16 17;\n";
	cmd += "SET COLOR_LAYER 17 16;\n";
	cmd += "SET COLOR_LAYER 18 16;\n";
	cmd += "SET COLOR_LAYER 29 18;\n";
	cmd += "SET FILL_LAYER 29 solid;\n";
	cmd += "SET COLOR_LAYER 30 18;\n";
	cmd += "SET FILL_LAYER 30 solid;\n";
	//cmd += "SET COLOR_LAYER 124 18;\n";
	//cmd += "SET COLOR_LAYER 120 20;\n";
	cmd += "SET COLOR_LAYER 26 21;\n";
	//cmd += "SET COLOR_LAYER 121 21;\n";
	cmd += "SET COLOR_LAYER 21 21;\n";
	cmd += "SET COLOR_LAYER 25 21;\n";
	cmd += "SET COLOR_LAYER 27 21;\n";
	cmd += "SET COLOR_LAYER 51 21;\n";
	//cmd += "SET COLOR_LAYER 122 21;\n";
	cmd += "SET COLOR_LAYER 22 21;\n";
	cmd += "SET COLOR_LAYER 26 21;\n";
	cmd += "SET COLOR_LAYER 28 21;\n";
	cmd += "SET COLOR_LAYER 52 21;\n";
	cmd += "SET COLOR_LAYER 20 20;\n";

	//cmd += "SET COLOR_LAYER 125 18;\n";
	//cmd += "SET COLOR_LAYER 126 18;\n";
	//cmd += "SET COLOR_LAYER 127 20;\n";

	cmd += "SET PALETTE 16 " + colorCopper + ";\n";
	cmd += "SET PALETTE 17 " + colorCopper + ";\n";
	cmd += "SET PALETTE 18 " + colorPlating + ";\n";
	cmd += "SET PALETTE 20 0xFF000000;\n";
	cmd += "SET PALETTE 21 " + colorSilkscreen + ";\n";
	cmd += "SET PALETTE 8 0xFFFFFFFF;\n";

	if(EAGLE_VERSION > 5 || (EAGLE_VERSION == 5 && EAGLE_RELEASE >= 11) ) { //Support for SET CONFIRM form Eagle 5.11 on
		cmd += "SET CONFIRM YES;\n";
	}

	if(height*real(resolution)*width*real(resolution)*real(bytePerPixel)>ram){
		resolution = int(sqrt(ram/(height*width*bytePerPixel)));

		string tmp;
		sprintf(tmp,":PCB image would be to large to export <br>Resolution will be set to: %ddpi",resolution);
		dlgMessageBox(tmp);
	}

	if(exportTop)
	{
		cmd += "DISPLAY NONE;DISPLAY 1 18 29 "+tsilcLayers+" "+versionLayer+";\n";
		if (imgExport) {
			sprintf(cmd, "%s EXPORT IMAGE '%s' %d;\n", cmd, topImage, resolution);
		}
		
		if (pdfExport) {
			if(frame){
				cmd += updateFrameInformation("PCB - Top");
				cmd += "DISPLAY NONE;DISPLAY 1 18 29 "+tsilcLayers+" "+versionLayer+" 153;\n";
			}
			sprintf(cmd,"%s PRINT SHEETS ALL HIERARCHY -BLACK PAPER %s FILE '%s';\n", cmd, (format?"A3 landscape":"A4 portrait"), topPdf);
		}
		
	}
	if(exportBot)
	{
		cmd += "DISPLAY NONE;DISPLAY 16 18 30 "+bsilcLayers+" "+versionLayer+";\n";
		if (imgExport) {
			sprintf(cmd, "%s EXPORT IMAGE '%s' %d;\n", cmd, botImage, resolution);
		}
		
		if (pdfExport) {
			if(frame){
				cmd += updateFrameInformation("PCB - Bottom");
				cmd += "DISPLAY NONE;DISPLAY 16 18 30 "+bsilcLayers+" "+versionLayer+" 153;\n";
			}
			sprintf(cmd,"%s PRINT SHEETS ALL HIERARCHY -BLACK PAPER %s FILE '%s';\n", cmd, (format?"A3 landscape":"A4 portrait"), botPdf);
		}
		
	}


	if(EAGLE_VERSION > 5 || (EAGLE_VERSION == 5 && EAGLE_RELEASE >= 11) ) //Support for SET CONFIRM form Eagle 5.11 on
	{
		cmd += "SET CONFIRM NO;\n";
	}

	//cmd += "SET PALETTE 0 0xFFFFFFFF;\n";

	cmd += "SET COLOR_LAYER 1 4;\n";
	cmd += "SET COLOR_LAYER 16 1;\n";
	cmd += "SET COLOR_LAYER 17 2;\n";
	cmd += "SET COLOR_LAYER 18 2;\n";
	

	string layers = "";

	board(B)
	{
		
		B.layers(L)
		{
			if(L.visible)
			{
				sprintf(layers, layers + " %d", L.number);
			}
		}
	}

	cmd += "DISPLAY NONE; DISPLAY " + layers + ";\n";

	if(palette(-1) == PALETTE_BLACK)
	{
		cmd += "SET PALETTE BLACK;\n";
	}
	else if(palette(-1) == PALETTE_WHITE)
	{
		cmd += "SET PALETTE WHITE;\n";
	}
	else
	{
		cmd += "SET PALETTE COLORED;\n";
	}

	cmd += "SET FILL_LAYER 29 LtSlash;\n";
	cmd += "SET FILL_LAYER 30 BkSlash;\n";
	
	if(exportBot && crop && imgExport)
	{
		sprintf(cmd, "%s RUN %sCropColor.ulp '%s' %d '%s';\n", cmd, getUlpDir("Include_"), botImage, resolution,filesetext(bname,".bat"));
	}
	if(exportTop && crop && imgExport)
	{
		sprintf(cmd, "%s RUN %sCropColor.ulp '%s' %d '%s';\n", cmd, getUlpDir("Include_"), topImage, resolution,filesetext(bname,".bat"));
	}

	if(exportBot && mirror && imgExport)
	{
		sprintf(cmd, "%s RUN %sMirrorColor.ulp '%s' '%s';\n", cmd, getUlpDir("Include_"), botImage,filesetext(bname,".bat"));
	}	
	
	executeAndExit(cmd);
}

exportImages(strtol(argv[1]),strtol(argv[2]),strtol(argv[3]),argv[4],argv[5],strtol(argv[6]),argv[7],argv[8],strtol(argv[9]),strtol(argv[10]),strtol(argv[11]), argv[12], argv[13], argv[14], argv[15], argv[16], argv[17], strtol(argv[18]), strtol(argv[19]));
