/************************************************************/
/* Include_BomConfig.ulp                                    */
/* - Contains defines for proper BOM generator			    */
/************************************************************/
/* (c) Copyright 2016, Bernhard Wörndl-Aichriedler          */
/* xDevelop OG - Hardware Developer							*/
/* E-Mail: bwa@xdevelop.Autors            				    */
/* Homepage: www.xdevelop.at 								*/
/************************************************************/
/* Letzte Änderung am 15.02.2016                            */
/* Version 1.0 				                                */
/************************************************************/

string BOM_PART_CATEGORIES[]	= {
	"Resistor", "Potentiometer", 			//0
	"Capacitor", "Polarized Capacitor",		//2
	"Inductor", "Diode", 					//4
	"Zener Diode", "LED", 					//6
	"Transistor N", "Transistor P", 		//8
	"MOSFET N", "MOSFET P",					//10
	"Analog IC", "Digital IC", 				//12
	"Voltage Regulator", "Display",			//14
	"Push button", "Switch", 				//16
	"Connector", "Fuse", 					//18
	"Transformer", "Speaker", 				//20
	"Buzzer", "Crystal", 					//22
	"Sensor", "Sub-Assembly", 				//24
	"Fiducial",	"Testpin",					//26
	"Antenna", "Balun",					//28
	"other"									//100
};

string BOM_PREDEFINED_NOTES[] = {
	"Use any part with similar tolerance.", 
	"Use specific part or suggest replacement", 
	"Use specific part", 
	"Or equivalent"
};

string BOM_WILDCARD_STR				= "%%";

/* Part definition - devices are sorted by id */
int BOM_PART_RESISTOR				= 0;
int BOM_PART_RPOT					= 1;
int BOM_PART_CAPACITOR				= 2;
int BOM_PART_CAPACITOR_POLARIZED	= 3;
int BOM_PART_INDUCTOR				= 4;

int BOM_PART_DIODE					= 5;
int BOM_PART_ZENER_DIODE			= 6;
int BOM_PART_LED					= 7;
int BOM_PART_TRANS_N				= 8;
int BOM_PART_TRANS_P				= 9;
int BOM_PART_FET_N					= 10;
int BOM_PART_FET_P					= 11;

int BOM_PART_IC_ANALOG				= 12;
int BOM_PART_IC_DIGITAL				= 13;
int BOM_PART_VREG					= 14;
int BOM_PART_DISP					= 15;

int BOM_PART_PUSH_BUTTON			= 16;
int BOM_PART_SWITCH					= 17;
int BOM_PART_CONNECTOR				= 18;
int BOM_PART_FUSE					= 19;
int BOM_PART_TRAFO					= 20;
int BOM_PART_SPEAKER				= 21;
int BOM_PART_BUZZER					= 22;
int BOM_PART_QUARZ					= 23;
int BOM_PART_SENSOR					= 24;
int BOM_PART_SUBASSEMBLY			= 25;
int BOM_PART_FIDUCIAL				= 26;
int BOM_PART_TESTPIN				= 27;
int BOM_PART_ANTENNA				= 28;
int BOM_PART_BALUN					= 29;

int BOM_PART_UNRECOGNISED			= 100;

/* Data Info arrays */

int 	BOM_DATA_PART_ID				[];
int		BOM_DATA_PARSE_VALUE			[];
string 	BOM_DATA_NAME 					[];
string 	BOM_DATA_NOTE					[];
string 	BOM_DATA_GP1					[];
string 	BOM_DATA_GP2					[];
string 	BOM_DATA_GP3					[];
string 	BOM_DATA_GP4					[];
string 	BOM_DATA_GP5					[];
int		BOM_DATA_HIDE_IN_BOM			[];
string 	BOM_DATA_IN_FIELD_PARTS 		[];
string 	BOM_DATA_IN_FIELD_VALUE 		[];
string 	BOM_DATA_IN_FIELD_PACKAGE 		[];
string 	BOM_DATA_IN_FIELD_DESCRIPTION 	[];
string 	BOM_DATA_IN_FIELD_DEVICE 		[];


/* 

  PART DEFINITIONS

*/
int BOM_DATA_COUNT = 0;


/* Potentiometer */
BOM_DATA_PART_ID[BOM_DATA_COUNT]			= BOM_PART_RPOT;
BOM_DATA_PARSE_VALUE[BOM_DATA_COUNT]		= 1;
BOM_DATA_NAME[BOM_DATA_COUNT]				= "POT";
BOM_DATA_NOTE[BOM_DATA_COUNT]				= "%%PSIZE%% %%GRID%%";
BOM_DATA_GP1[BOM_DATA_COUNT]				= "%%PSIZE%%";
BOM_DATA_GP2[BOM_DATA_COUNT]				= "%%GRID%%";
BOM_DATA_GP3[BOM_DATA_COUNT]				= "";
BOM_DATA_GP4[BOM_DATA_COUNT]				= "%%VALUE%%";
BOM_DATA_GP5[BOM_DATA_COUNT]				= "%%PARSED_VALUE%%";
BOM_DATA_IN_FIELD_PARTS[BOM_DATA_COUNT] 	= "R*";
BOM_DATA_IN_FIELD_VALUE[BOM_DATA_COUNT] 	= "";
BOM_DATA_IN_FIELD_DEVICE[BOM_DATA_COUNT]	= "TRIM*";
BOM_DATA_IN_FIELD_PACKAGE[BOM_DATA_COUNT]	= "";
BOM_DATA_IN_FIELD_DESCRIPTION[BOM_DATA_COUNT] 	= "";	
BOM_DATA_HIDE_IN_BOM[BOM_DATA_COUNT]		= 0;

/* Resistors */
BOM_DATA_COUNT++;
BOM_DATA_PART_ID[BOM_DATA_COUNT]		= BOM_PART_RESISTOR;
BOM_DATA_PARSE_VALUE[BOM_DATA_COUNT]		= 1;
BOM_DATA_NAME[BOM_DATA_COUNT]			= "RES";
BOM_DATA_NOTE[BOM_DATA_COUNT]			= "%%PSIZE%% %%GRID%%";
BOM_DATA_GP1[BOM_DATA_COUNT]			= "%%PSIZE%%";
BOM_DATA_GP2[BOM_DATA_COUNT]			= "%%GRID%%";
BOM_DATA_GP3[BOM_DATA_COUNT]			= "";
BOM_DATA_GP4[BOM_DATA_COUNT]			= "%%VALUE%%";
BOM_DATA_GP5[BOM_DATA_COUNT]			= "%%PARSED_VALUE%%";
BOM_DATA_IN_FIELD_PARTS[BOM_DATA_COUNT] 	= "R*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* TODO - RPOT */

/* Polarized Caps */
BOM_DATA_COUNT++;
BOM_DATA_PART_ID[BOM_DATA_COUNT]		= BOM_PART_CAPACITOR_POLARIZED;
BOM_DATA_PARSE_VALUE[BOM_DATA_COUNT]		= 1;
BOM_DATA_NAME[BOM_DATA_COUNT]			= "POL-CAP";
BOM_DATA_NOTE[BOM_DATA_COUNT]			= "%%PSIZE%% %%GRID%%";
BOM_DATA_GP1[BOM_DATA_COUNT]			= "%%PSIZE%%";
BOM_DATA_GP2[BOM_DATA_COUNT]			= "%%GRID%%";
BOM_DATA_GP3[BOM_DATA_COUNT]			= "";
BOM_DATA_GP4[BOM_DATA_COUNT]			= "%%VALUE%%";
BOM_DATA_GP5[BOM_DATA_COUNT]			= "%%PARSED_VALUE%%";
BOM_DATA_IN_FIELD_PARTS[BOM_DATA_COUNT] 	= "C*";
BOM_DATA_IN_FIELD_VALUE[BOM_DATA_COUNT] 	= "";
BOM_DATA_IN_FIELD_DEVICE[BOM_DATA_COUNT]	= "CPOL*";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* Caps */
BOM_DATA_COUNT++;
BOM_DATA_PART_ID[BOM_DATA_COUNT]		= BOM_PART_CAPACITOR;
BOM_DATA_PARSE_VALUE[BOM_DATA_COUNT]		= 1;
BOM_DATA_NAME[BOM_DATA_COUNT]			= "CAP";
BOM_DATA_NOTE[BOM_DATA_COUNT]			= "%%PSIZE%% %%GRID%%";
BOM_DATA_GP1[BOM_DATA_COUNT]			= "%%PSIZE%%";
BOM_DATA_GP2[BOM_DATA_COUNT]			= "%%GRID%%";
BOM_DATA_GP3[BOM_DATA_COUNT]			= "";
BOM_DATA_GP4[BOM_DATA_COUNT]			= "%%VALUE%%";
BOM_DATA_GP5[BOM_DATA_COUNT]			= "%%PARSED_VALUE%%";
BOM_DATA_IN_FIELD_PARTS[BOM_DATA_COUNT] 	= "C*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* Inductors */
BOM_DATA_COUNT++;
BOM_DATA_PART_ID[BOM_DATA_COUNT]		= BOM_PART_INDUCTOR;
BOM_DATA_PARSE_VALUE[BOM_DATA_COUNT]		= 1;
BOM_DATA_NAME[BOM_DATA_COUNT]			= "IND";
BOM_DATA_NOTE[BOM_DATA_COUNT]			= "%%PSIZE%% %%GRID%%";
BOM_DATA_GP1[BOM_DATA_COUNT]			= "%%PSIZE%%";
BOM_DATA_GP2[BOM_DATA_COUNT]			= "%%GRID%%";
BOM_DATA_GP3[BOM_DATA_COUNT]			= "";
BOM_DATA_GP4[BOM_DATA_COUNT]			= "%%VALUE%%";
BOM_DATA_GP5[BOM_DATA_COUNT]			= "%%PARSED_VALUE%%";
BOM_DATA_IN_FIELD_PARTS[BOM_DATA_COUNT] 	= "L*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* Zener Diode */
BOM_DATA_COUNT++;
BOM_DATA_PART_ID[BOM_DATA_COUNT]		= BOM_PART_ZENER_DIODE;
BOM_DATA_PARSE_VALUE[BOM_DATA_COUNT]		= 1;
BOM_DATA_NAME[BOM_DATA_COUNT]			= "ZENER";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "V*";
BOM_DATA_IN_FIELD_VALUE[BOM_DATA_COUNT] 	= "";
BOM_DATA_IN_FIELD_DEVICE[BOM_DATA_COUNT]	= "ZENER-DIODE*";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* DISPLAY */
BOM_DATA_COUNT++;
BOM_DATA_PART_ID[BOM_DATA_COUNT]		= BOM_PART_DISP;
BOM_DATA_PARSE_VALUE[BOM_DATA_COUNT]	= 0;
BOM_DATA_NAME[BOM_DATA_COUNT]			= "DISP";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "H*";
BOM_DATA_IN_FIELD_VALUE[BOM_DATA_COUNT] 	= "";
BOM_DATA_IN_FIELD_DEVICE[BOM_DATA_COUNT]	= "";
BOM_DATA_IN_FIELD_PACKAGE[BOM_DATA_COUNT]	= "*LCD*";
BOM_DATA_IN_FIELD_DESCRIPTION[BOM_DATA_COUNT] 	= "";
BOM_DATA_HIDE_IN_BOM[BOM_DATA_COUNT]		= 0;


/* 7 SEGMENT */
BOM_DATA_COUNT++;
BOM_DATA_PART_ID[BOM_DATA_COUNT]		= BOM_PART_DISP;
BOM_DATA_PARSE_VALUE[BOM_DATA_COUNT]		= 0;
BOM_DATA_NAME[BOM_DATA_COUNT]			= "DISP";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "H*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "*7 segment*";
BOM_DATA_HIDE_IN_BOM[BOM_DATA_COUNT]		= 0;

/* LED */
BOM_DATA_COUNT++;
BOM_DATA_PART_ID[BOM_DATA_COUNT]		= BOM_PART_LED;
BOM_DATA_PARSE_VALUE[BOM_DATA_COUNT]		= 0;
BOM_DATA_NAME[BOM_DATA_COUNT]			= "LED";
BOM_DATA_NOTE[BOM_DATA_COUNT]			= "%%PSIZE%%";
BOM_DATA_GP1[BOM_DATA_COUNT]			= "%%PSIZE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "H*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* LED */
BOM_DATA_COUNT++;
BOM_DATA_PART_ID[BOM_DATA_COUNT]		= BOM_PART_LED;
BOM_DATA_PARSE_VALUE[BOM_DATA_COUNT]		= 0;
BOM_DATA_NAME[BOM_DATA_COUNT]			= "LED";
BOM_DATA_NOTE[BOM_DATA_COUNT]			= "%%PSIZE%%";
BOM_DATA_GP1[BOM_DATA_COUNT]			= "%%PSIZE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "V*";
BOM_DATA_IN_FIELD_VALUE[BOM_DATA_COUNT] 	= "";
BOM_DATA_IN_FIELD_DEVICE[BOM_DATA_COUNT]	= "LED*";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* LED */
BOM_DATA_COUNT++;
BOM_DATA_PART_ID[BOM_DATA_COUNT]		= BOM_PART_LED;
BOM_DATA_PARSE_VALUE[BOM_DATA_COUNT]		= 0;
BOM_DATA_NAME[BOM_DATA_COUNT]			= "LED";
BOM_DATA_NOTE[BOM_DATA_COUNT]			= "%%PSIZE%%";
BOM_DATA_GP1[BOM_DATA_COUNT]			= "%%PSIZE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "V*";
BOM_DATA_IN_FIELD_VALUE[BOM_DATA_COUNT] 	= "";
BOM_DATA_IN_FIELD_DEVICE[BOM_DATA_COUNT]	= "";
BOM_DATA_IN_FIELD_PACKAGE[BOM_DATA_COUNT]	= "LED*";
BOM_DATA_IN_FIELD_DESCRIPTION[BOM_DATA_COUNT] 	= "";
BOM_DATA_HIDE_IN_BOM[BOM_DATA_COUNT]		= 0;

/* LED */
BOM_DATA_COUNT++;
BOM_DATA_PART_ID[BOM_DATA_COUNT]		= BOM_PART_LED;
BOM_DATA_PARSE_VALUE[BOM_DATA_COUNT]		= 0;
BOM_DATA_NAME[BOM_DATA_COUNT]			= "LED";
BOM_DATA_NOTE[BOM_DATA_COUNT]			= "%%PSIZE%%";
BOM_DATA_GP1[BOM_DATA_COUNT]			= "%%PSIZE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "V*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "LED*";
BOM_DATA_HIDE_IN_BOM[BOM_DATA_COUNT]		= 0;

/* NORMAL DIODE */
BOM_DATA_COUNT++;
BOM_DATA_PART_ID[BOM_DATA_COUNT]		= BOM_PART_DIODE;
BOM_DATA_PARSE_VALUE[BOM_DATA_COUNT]		= 0;
BOM_DATA_NAME[BOM_DATA_COUNT]			= "DIODE";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "V*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* VREG */
BOM_DATA_COUNT++;
BOM_DATA_PART_ID[BOM_DATA_COUNT]		= BOM_PART_VREG;
BOM_DATA_PARSE_VALUE[BOM_DATA_COUNT]		= 0;
BOM_DATA_NAME[BOM_DATA_COUNT]			= "VREG";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "N*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "*VOLTAGE REGULATOR*";
BOM_DATA_HIDE_IN_BOM[BOM_DATA_COUNT]		= 0;


/* IC - Analog */
BOM_DATA_COUNT++;
BOM_DATA_PART_ID[BOM_DATA_COUNT]		= BOM_PART_IC_ANALOG;
BOM_DATA_PARSE_VALUE[BOM_DATA_COUNT]		= 0;
BOM_DATA_NAME[BOM_DATA_COUNT]			= "IC";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "N*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* IC - Digital */
BOM_DATA_COUNT++;
BOM_DATA_PART_ID[BOM_DATA_COUNT]		= BOM_PART_IC_DIGITAL;
BOM_DATA_PARSE_VALUE[BOM_DATA_COUNT]		= 0;
BOM_DATA_NAME[BOM_DATA_COUNT]			= "IC";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "D*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* Button */
BOM_DATA_COUNT++;
BOM_DATA_PART_ID[BOM_DATA_COUNT]		= BOM_PART_SWITCH;
BOM_DATA_PARSE_VALUE[BOM_DATA_COUNT]		= 0;
BOM_DATA_NAME[BOM_DATA_COUNT]			= "BTN";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "S*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* Connectors */
BOM_DATA_COUNT++;
BOM_DATA_PART_ID[BOM_DATA_COUNT]		= BOM_PART_CONNECTOR;
BOM_DATA_PARSE_VALUE[BOM_DATA_COUNT]		= 0;
BOM_DATA_NAME[BOM_DATA_COUNT]			= "CON";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "X*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* Fuse */
BOM_DATA_COUNT++;
BOM_DATA_PART_ID[BOM_DATA_COUNT]		= BOM_PART_FUSE;
BOM_DATA_PARSE_VALUE[BOM_DATA_COUNT]		= 0;
BOM_DATA_NAME[BOM_DATA_COUNT]			= "FUSE";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "F*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* Trafo */
BOM_DATA_COUNT++;
BOM_DATA_PART_ID[BOM_DATA_COUNT]		= BOM_PART_TRAFO;
BOM_DATA_PARSE_VALUE[BOM_DATA_COUNT]		= 0;
BOM_DATA_NAME[BOM_DATA_COUNT]			= "TRAFO";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "T*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* Quarz */
BOM_DATA_COUNT++;
BOM_DATA_PART_ID[BOM_DATA_COUNT]		= BOM_PART_QUARZ;
BOM_DATA_PARSE_VALUE[BOM_DATA_COUNT]		= 0;
BOM_DATA_NAME[BOM_DATA_COUNT]			= "XTAL";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "B*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* Quarz */
BOM_DATA_COUNT++;
BOM_DATA_PART_ID[BOM_DATA_COUNT]		= BOM_PART_SENSOR;
BOM_DATA_PARSE_VALUE[BOM_DATA_COUNT]		= 0;
BOM_DATA_NAME[BOM_DATA_COUNT]			= "SEN";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "B*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* Fiducal */
BOM_DATA_COUNT++;
BOM_DATA_PART_ID[BOM_DATA_COUNT]		= BOM_PART_FIDUCIAL;
BOM_DATA_PARSE_VALUE[BOM_DATA_COUNT]		= 0;
BOM_DATA_NAME[BOM_DATA_COUNT]			= "FID";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "J*";
BOM_DATA_IN_FIELD_VALUE[BOM_DATA_COUNT] 	= "";
BOM_DATA_IN_FIELD_DEVICE[BOM_DATA_COUNT]	= "";
BOM_DATA_IN_FIELD_PACKAGE[BOM_DATA_COUNT]	= "PM*";
BOM_DATA_IN_FIELD_DESCRIPTION[BOM_DATA_COUNT] 	= "";
BOM_DATA_HIDE_IN_BOM[BOM_DATA_COUNT]		= 1;

/* Fiducal */
BOM_DATA_COUNT++;
BOM_DATA_PART_ID[BOM_DATA_COUNT]		= BOM_PART_TESTPIN;
BOM_DATA_PARSE_VALUE[BOM_DATA_COUNT]		= 0;
BOM_DATA_NAME[BOM_DATA_COUNT]			= "PIN";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "P*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 1;

/* Antenna */
BOM_DATA_COUNT++;
BOM_DATA_PART_ID[BOM_DATA_COUNT]		= BOM_PART_ANTENNA;
BOM_DATA_PARSE_VALUE[BOM_DATA_COUNT]		= 0;
BOM_DATA_NAME[BOM_DATA_COUNT]			= "ANT";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "W*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;

/* Balun */
BOM_DATA_COUNT++;
BOM_DATA_PART_ID[BOM_DATA_COUNT]		= BOM_PART_BALUN;
BOM_DATA_PARSE_VALUE[BOM_DATA_COUNT]		= 0;
BOM_DATA_NAME[BOM_DATA_COUNT]			= "BALUN";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "W*";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";
BOM_DATA_HIDE_IN_BOM[BOM_DATA_COUNT]		= 0;


/* OTHER PARTS */
BOM_DATA_COUNT++;
BOM_DATA_PART_ID[BOM_DATA_COUNT]		= BOM_PART_UNRECOGNISED;
BOM_DATA_PARSE_VALUE[BOM_DATA_COUNT]		= 0;
BOM_DATA_NAME[BOM_DATA_COUNT]			= "";
BOM_DATA_NOTE[BOM_DATA_COUNT]			= "%%PACKAGE%%";
BOM_DATA_GP1[BOM_DATA_COUNT]			= "%%PACKAGE%%";
BOM_DATA_GP2[BOM_DATA_COUNT]			= "";
BOM_DATA_GP3[BOM_DATA_COUNT]			= "";
BOM_DATA_GP4[BOM_DATA_COUNT]			= "%%VALUE%%";
BOM_DATA_GP5[BOM_DATA_COUNT]			= "";
BOM_DATA_IN_FIELD_PARTS[BOM_DATA_COUNT] 	= "";
BOM_DATA_IN_FIELD_VALUE[BOM_DATA_COUNT] 	= "";
BOM_DATA_IN_FIELD_DEVICE[BOM_DATA_COUNT]	= "";
BOM_DATA_IN_FIELD_PACKAGE[BOM_DATA_COUNT]	= "";
BOM_DATA_IN_FIELD_DESCRIPTION[BOM_DATA_COUNT] 	= "";

BOM_DATA_COUNT++;
