#include "Include_Boardsize.ulp"
#include "Include_FastExecute.ulp";


void dbgMsg(string msg,real val){
	//to prevent debug messages to apear in releace
	string tmp="";
	sprintf(tmp,msg+"%f",val);
	dlgMessageBox(tmp);
}


real wireX1[];
real wireY1[];
real wireX2[];
real wireY2[];
real wireRad[];

real potMitX[];
real potMitY[];

int wireCount=0;
int cclockwise=0;

int gapWidth = 2; //distance between board and panel inline in mm
int panelWidthX = 5, panelWidthY = 5; //min distance between panel inline and panel outline in mm 

int infinety = 1000000000;	//since the max board size is 338 x 238, 1000000000 is aproximatly infinety

string cmd = "";
string lib = "";
string brd = "";

void reverseDirection(int index){
	wireX2[index] = wireX2[index] + wireX1[index];
	wireX1[index] = wireX2[index] - wireX1[index];
	wireX2[index] = wireX2[index] - wireX1[index];

	wireY2[index] = wireY2[index] + wireY1[index];
	wireY1[index] = wireY2[index] - wireY1[index];
	wireY2[index] = wireY2[index] - wireY1[index];

	wireRad[index]*=-1;
}

void swopPlaces(int index1, int index2){
	real tmp;

	tmp				= wireX1[index1];
	wireX1[index1] 	= wireX1[index2];
	wireX1[index2] 	= tmp;

	tmp				= wireY1[index1];
	wireY1[index1] 	= wireY1[index2];
	wireY1[index2] 	= tmp;

	tmp				= wireX2[index1];
	wireX2[index1] 	= wireX2[index2];
	wireX2[index2] 	= tmp;

	tmp				= wireY2[index1];
	wireY2[index1] 	= wireY2[index2];
	wireY2[index2] 	= tmp;

	tmp 			= wireRad[index1];
	wireRad[index1] = wireRad[index2];
	wireRad[index2] = tmp;
}

void deletWirePart(real startX, real startY, real endX, real endY){
	sprintf(cmd,"%sCHANGE WIDTH 0.5mm;\n",cmd);
	sprintf(cmd,"%sWIRE (%fmm %fmm) (%fmm %fmm);\n",cmd,startX,startY,endX,endY);
	sprintf(cmd,"%sDELETE (%fmm %fmm);\n",cmd,startX,startY);
	sprintf(cmd,"%sCHANGE WIDTH 0.15mm;\n",cmd);
}

void main(){

	

	getBoardSize();

	real maxX = u2mm(max_x);
	real minX = u2mm(min_x);
	real maxY = u2mm(max_y);
	real minY = u2mm(min_y);

	real lenX = maxX-minX;
	real lenY = maxY-minY;

	real centerX = minX+(lenX/2);
	real centerY = minY+(lenY/2);

	sprintf(cmd, "WRITE;\n");

	/*Check, if board fits in, if not, return Error message and don't run rest of ulp/create frame and stencil*/

	if(lenX > 338 || lenX < 38 || lenY > 238 || lenY < 38){

	   dlgMessageBox(":Error!\nUnable to export panel\nBoard Size must be within: \n\n" + "x: 38mm - 338mm" + "\n" + "y: 38mm - 238mm"); 

	   exit("");
	}

	//saving the board-dimensions within an array
	board(B){
		brd=B.name;
		lib=filedir(B.name)+"fabrication.lbr";

		int i=0;
		B.wires(W){
			if(W.layer == 20){
				wireX1[i]=u2mm(W.x1);
				wireY1[i]=u2mm(W.y1);
				wireX2[i]=u2mm(W.x2);
				wireY2[i]=u2mm(W.y2);

				if(W.arc){
					wireRad[i]=(W.arc.radius/320000);//to convert to mm
				}
				else{
					wireRad[i]=0;
				}
				i++;
			}
		}
		wireCount=i;
	}

	cclockwise=0;
	//sorting the board-dimensions
	for(int i=1; i<wireCount; i++){
		if((wireX1[i]==wireX2[i-1])&&(wireY1[i]==wireY2[i-1])){
		}
		else if ((wireX2[i]==wireX2[i-1])&&(wireY2[i]==wireY2[i-1])){
			//reversing the direction of the wire so every wire either gos cclockwise or countercclockwise
			reverseDirection(i);
		}
		else{
			for(int j=i+1;j<wireCount;j++){
				if((wireX1[j]==wireX2[i-1])&&(wireY1[j]==wireY2[i-1])){
					swopPlaces(i,j);
					break;
				}
				else if((wireX2[j]==wireX2[i-1])&&(wireY2[j]==wireY2[i-1])){
					swopPlaces(i,j);

					//reversing the direction of the wire so every wire either gos cclockwise or countercclockwise
					reverseDirection(i);

					break;
				}
			}
		}
	
		//determerning wire direction
		if((wireX1[i]>centerX)&&(wireX2[i]>centerX)&&(wireY1[i]>centerY)&&(wireY2[i]>centerY)) {
			//I
			if((wireX1[i]>wireX2[i])||(wireY1[i]<wireY2[i])) {
				cclockwise++;
			}
			else {
				cclockwise--;
			}
		}
		else if((wireX1[i]<centerX)&&(wireX2[i]<centerX)&&(wireY1[i]>centerY)&&(wireY2[i]>centerY)) {
			//II
			if((wireX1[i]>wireX2[i])||(wireY1[i]>wireY2[i])) {
				cclockwise++;
			}
			else {
				cclockwise--;
			}
		}
		else if((wireX1[i]<centerX)&&(wireX2[i]<centerX)&&(wireY1[i]<centerY)&&(wireY2[i]<centerY)) {
			//III
			if((wireX1[i]<wireX2[i])||(wireY1[i]>wireY2[i])) {
				cclockwise++;
			}
			else {
				cclockwise--;
			}
		}
		else if((wireX1[i]>centerX)&&(wireX2[i]>centerX)&&(wireY1[i]<centerY)&&(wireY2[i]<centerY)) {
			//IV
			if((wireX1[i]<wireX2[i])||(wireY1[i]<wireY2[i])) {
				cclockwise++;
			}
			else {
				cclockwise--;
			}
		}
		else if((wireY1[i]>centerY)&&(wireY2[i]>centerY)) {
			//I&II
			if(wireX1[i]>wireX2[i]) {
				cclockwise++;
			}
			else {
				cclockwise--;
			}
		}
		else if((wireX1[i]<centerX)&&(wireX2[i]<centerX)) {
			//II&III
			if(wireY1[i]>wireY2[i]) {
				cclockwise++;
			}
			else {
				cclockwise--;
			}
		}
		else if((wireY1[i]<centerY)&&(wireY2[i]<centerY)) {
			//III&IV
			if(wireX1[i]<wireX2[i]) {
				cclockwise++;
			}
			else {
				cclockwise--;
			}
		}
		else if((wireX1[i]>centerX)&&(wireX2[i]>centerX)) {
			//IV&I
			if(wireY1[i]<wireY2[i]) {
				cclockwise++;
			}
			else {
				cclockwise--;
			}
		}
	}

	if(cclockwise>0){
		cclockwise=1;
	}
	else if(cclockwise<0){
		cclockwise=-1;
	}
	else{
		dlgMessageBox(":Unable to produce a panel");
		exit("");
	}

	//start writing the script
	cmd = "";

	sprintf(cmd, "%s DISPLAY NONE;\n", cmd);

	sprintf(cmd, "%s SET CONFIRM YES;\n", cmd);
	sprintf(cmd, "%s LAYER DIMENSION;\n", cmd);
	sprintf(cmd, "%s CHANGE WIDTH 0.15mm;\n", cmd);

	sprintf(cmd, "%s GROUP ALL;\n", cmd);
	sprintf(cmd, "%s CHANGE WIDTH 0.15mm (>0 0);\n", cmd);
	sprintf(cmd, "%s SET WIRE_BEND 2;\n", cmd);

	//crearing the panel-outline
	real x_min_outline = minX-(panelWidthX+gapWidth);
	real x_max_outline = maxX+(panelWidthX+gapWidth);
	real y_min_outline = minY-(panelWidthY+gapWidth);
	real y_max_outline = maxY+(panelWidthY+gapWidth);

	sprintf(cmd, "%s WIRE 'outline_panel' (%fmm %fmm) (%fmm %fmm) (%fmm %fmm) (%fmm %fmm) (%fmm %fmm);\n", cmd, x_min_outline, y_min_outline, x_max_outline, y_min_outline, x_max_outline, y_max_outline, x_min_outline, y_max_outline, x_min_outline, y_min_outline);

	//creating the panel-inline 
	real drawX=0.0, drawY=0.0, oriX=0.0, oriY=0.0, tmpX=0.0, tmpY=0.0, drawR=0.0;

	for(int n=0;n<wireCount;n++){
		drawR=1;

		potMitX[n]=0;
		potMitY[n]=0;
		//seting the start point
		
		if(n==0){ 
			if(wireRad[n]){

				drawX=wireX1[n];
				drawY=wireY1[n];

				if(cclockwise>0){
					if(wireRad[n]>0){
						if((wireX1[n]>wireX2[n])&&(wireY1[n]>wireY2[n])){
							drawY+=gapWidth;
						}
						else if((wireX1[n]>wireX2[n])&&(wireY1[n]<wireY2[n])){
							drawX+=gapWidth;
						}
						else if((wireX1[n]<wireX2[n])&&(wireY1[n]>wireY2[n])){
							drawX-=gapWidth;
						}
						else if((wireX1[n]<wireX2[n])&&(wireY1[n]<wireY2[n])){
							drawY-=gapWidth;
						}
					}
					else{
						if((wireX1[n]>wireX2[n])&&(wireY1[n]>wireY2[n])){
							drawX+=gapWidth;
						}
						else if((wireX1[n]>wireX2[n])&&(wireY1[n]<wireY2[n])){
							drawY+=gapWidth;
						}
						else if((wireX1[n]<wireX2[n])&&(wireY1[n]>wireY2[n])){
							drawY-=gapWidth;
						}
						else if((wireX1[n]<wireX2[n])&&(wireY1[n]<wireY2[n])){
							drawX+=gapWidth;
						}
					}
				}
				else{
					if(wireRad[n]<0){
						if((wireX1[n]>wireX2[n])&&(wireY1[n]>wireY2[n])){
							drawX+=gapWidth;
						}
						else if((wireX1[n]>wireX2[n])&&(wireY1[n]<wireY2[n])){
							drawY-=gapWidth;
						}
						else if((wireX1[n]<wireX2[n])&&(wireY1[n]>wireY2[n])){
							drawY+=gapWidth;
						}
						else if((wireX1[n]<wireX2[n])&&(wireY1[n]<wireY2[n])){
							drawX-=gapWidth;
						}
					}
					else{
						if((wireX1[n]>wireX2[n])&&(wireY1[n]>wireY2[n])){
							drawY-=gapWidth;
						}
						else if((wireX1[n]>wireX2[n])&&(wireY1[n]<wireY2[n])){
							drawX-=gapWidth;
						}
						else if((wireX1[n]<wireX2[n])&&(wireY1[n]>wireY2[n])){
							drawX+=gapWidth;
						}
						else if((wireX1[n]<wireX2[n])&&(wireY1[n]<wireY2[n])){
							drawY+=gapWidth;
						}
					}
				}
			}
			else{
				//creating a normal vector and storing the signs
				tmpX = cclockwise*(wireY2[n]-wireY1[n]);
				tmpY = (-1)*cclockwise*(wireX2[n]-wireX1[n]);
				//to prvent a dividing by 0 error
				if(tmpX==0){
					drawX=0;
					drawY=(gapWidth)*(tmpY/abs(tmpY));
				}
				else if (tmpY==0) {
					drawX=(gapWidth)*(tmpX/abs(tmpX));
					drawY=0;
				} 
				else{
					//triming the vector and unsigning
					drawX=gapWidth*cos(atan(abs(tmpY/tmpX)));
					drawX=gapWidth*sin(atan(abs(tmpY/tmpX)));
					//resigning the normal vector
					drawX*=tmpX/abs(tmpX);
					drawY*=tmpY/abs(tmpY);
				}
				//ading the normal vector to the position vector
				drawX+=wireX1[n];
				drawY+=wireY1[n];
			}
			oriX=drawX;
			oriY=drawY;
			sprintf(cmd,"%sWIRE 'inline_panel' (%fmm %fmm)",cmd,drawX,drawY);
		}

		//seting endpoints 
		
		if(wireRad[n]){//drawing an arc
			//getting the radius right
			drawR=wireRad[n];
			drawR+=(cclockwise*gapWidth);

			if(drawR<0){
				sprintf(cmd,"%s @%f ",cmd,drawR);
			}
			else{
				sprintf(cmd,"%s @+%f",cmd,drawR);
			}

			//seting the end coordinates
			drawX=wireX2[n];
			drawY=wireY2[n];

			//Ajusting end coordinats
			if(cclockwise>0){
				if (wireRad[n]>0) {
					if((wireX1[n]>wireX2[n])&&(wireY1[n]>wireY2[n])){
						//dbgMsg("x- y- c:",n);
						drawX-=gapWidth;
					}
					else if((wireX1[n]>wireX2[n])&&(wireY1[n]<wireY2[n])){
						//dbgMsg("x- y+ c:",n);
						drawY+=gapWidth;
					}
					else if((wireX1[n]<wireX2[n])&&(wireY1[n]>wireY2[n])){
						//dbgMsg("x+ y- c:",n);
						drawY-=gapWidth;
					}
					else if((wireX1[n]<wireX2[n])&&(wireY1[n]<wireY2[n])){
						//dbgMsg("x+ y+ c:",n);
						drawX+=gapWidth;
					}
				}
				else {
					if((wireX1[n]>wireX2[n])&&(wireY1[n]>wireY2[n])){
						//dbgMsg("x- y- c:",n);
						drawY+=gapWidth;
					}
					else if((wireX1[n]>wireX2[n])&&(wireY1[n]<wireY2[n])){
						//dbgMsg("x- y+ c:",n);
						drawX+=gapWidth;
					}
					else if((wireX1[n]<wireX2[n])&&(wireY1[n]>wireY2[n])){
						//dbgMsg("x+ y- c:",n);
						drawX-=gapWidth;
					}
					else if((wireX1[n]<wireX2[n])&&(wireY1[n]<wireY2[n])){
						//dbgMsg("x+ y+ c:",n);
						drawY-=gapWidth;
					}
				}
			}
			else{
				if (wireRad[n]<0) {
					if((wireX1[n]>wireX2[n])&&(wireY1[n]>wireY2[n])){
						//dbgMsg("x- y- c!:",n);
						drawY-=gapWidth;
					}
					else if((wireX1[n]>wireX2[n])&&(wireY1[n]<wireY2[n])){
						//dbgMsg("x- y+ c!:",n);
						drawX-=gapWidth;
					}
					else if((wireX1[n]<wireX2[n])&&(wireY1[n]>wireY2[n])){
						//dbgMsg("x+ y- c!:",n);
						drawX+=gapWidth;
					}
					else if((wireX1[n]<wireX2[n])&&(wireY1[n]<wireY2[n])){
						//dbgMsg("x+ y+ c!:",n);
						drawY+=gapWidth;
					}
				}
				else {
					if((wireX1[n]>wireX2[n])&&(wireY1[n]>wireY2[n])){
						//dbgMsg("x- y- c!:",n);
						drawX+=gapWidth;
					}
					else if((wireX1[n]>wireX2[n])&&(wireY1[n]<wireY2[n])){
						//dbgMsg("x- y+ c!:",n);
						drawY-=gapWidth;
					}
					else if((wireX1[n]<wireX2[n])&&(wireY1[n]>wireY2[n])){
						//dbgMsg("x+ y- c!:",n);
						drawY+=gapWidth;
					}
					else if((wireX1[n]<wireX2[n])&&(wireY1[n]<wireY2[n])){
						//dbgMsg("x+ y+ c!:",n);
						drawX-=gapWidth;
					}
				}
			}
		}
		else {//drawing lines
			//creating a normal vector and storing the signs
			tmpX = cclockwise*(wireY2[n]-wireY1[n]);
			tmpY = -1*cclockwise*(wireX2[n]-wireX1[n]);
			//to prvent a dividing by 0 error
			if(tmpX==0){
				drawX=0;
				drawY=(gapWidth)*(tmpY/abs(tmpY));
			}
			else if (tmpY==0) {
				drawX=(gapWidth)*(tmpX/abs(tmpX));
				drawY=0;
			} 
			else{
				//triming the vector and unsigning
				drawX=gapWidth*cos(atan(abs(tmpY/tmpX)));
				drawY=gapWidth*sin(atan(abs(tmpY/tmpX)));
				//resigning the normal vector
				drawX*=tmpX/abs(tmpX);
				drawY*=tmpY/abs(tmpY);
			}
			//ading the normal vector to the position vector
			drawX+=wireX2[n];
			drawY+=wireY2[n];

			//to calculate corners									//does not work smoothly with angles other than 90°*x
			if(!wireRad[(n+1)%wireCount]){
				//calculating the next line within polarform
				real drawX1=0, drawY1=0, tmpX1=0, tmpY1=0;

				tmpX1 = cclockwise*(wireY2[(n+1)%wireCount]-wireY1[(n+1)%wireCount]);
				tmpY1 = (-1)*cclockwise*(wireX2[(n+1)%wireCount]-wireX1[(n+1)%wireCount]);
				//to prvent a dividing by 0 error
				if(tmpX1==0){
					drawX1=0;
					drawY1=(gapWidth)*(tmpY1/abs(tmpY1));
				}
				else if (tmpY1==0) {
					drawX1=(gapWidth)*(tmpX1/abs(tmpX1));
					drawY1=0;
				} 
				else{
					//triming the vector and unsigning
					drawX1=gapWidth*cos(atan(abs(tmpY1/tmpX1)));
					drawY1=gapWidth*sin(atan(abs(tmpY1/tmpX1)));
					//resigning the normal vector
					drawX1*=tmpX/abs(tmpX1);
					drawY1*=tmpY/abs(tmpY1);
				}
				//ading the normal vector to the position vector
				drawX1+=wireX1[(n+1)%wireCount];
				drawY1+=wireY1[(n+1)%wireCount];

				tmpX = (wireX2[n]-wireX1[n]);
				tmpY = (wireY2[n]-wireY1[n]);
				tmpX1 = (wireX2[(n+1)%wireCount]-wireX1[(n+1)%wireCount]);
				tmpY1 = (wireY2[(n+1)%wireCount]-wireY1[(n+1)%wireCount]);

				//converting the polarforms into linear functions (y=k*x+d)
				//from here on out tmpX==k, tmpY==d, tmpX1==k1 & tmpY1==d1

				//calculating k & k1
				if((tmpX==0) && (tmpX1==0)){
					//boath lines go in the same direction so wire[n] can be skipped
					continue;
				} 
				else if(tmpX==0) {
					tmpX=infinety;
					tmpX1=tmpY1/tmpX1;
				}
				else if(tmpX1==0) {
					tmpX=tmpY/tmpX;
					tmpX1=infinety;
				}
				else{
					tmpX=tmpY/tmpX;
					tmpX1=tmpY1/tmpX1;
				}

				if(tmpX==tmpX1){
					//boath lines go in the same direction so wire[n] can be skipped
					continue;
				}

				//calculating d & d1
				tmpY=drawY-(drawX*tmpX);
				tmpY1=drawY1-(drawX1*tmpX1);
				//calculating the point of interception
				drawX=(tmpY1-tmpY)/(tmpX-tmpX1);
				drawY=tmpX*drawX+tmpY;

				potMitX[n]=drawX;
				potMitY[n]=drawY;
			}
		}

		if(drawR!=0){ //to prvent clicking the same point twice
			sprintf(cmd,"%s (%fmm %fmm)\n",cmd,drawX,drawY);
		}
	}
	//to close the ring and to end the wire comand
	sprintf(cmd,"%s (%fmm %fmm);\n",cmd,oriX,oriY);
	

	//Creating a Bridg package
	cmd+="OPEN "+lib+";\n";
	cmd+="SET CONFIRM YES;\n";
	cmd+="EDIT bridg.pac;\n";
	//deleting previous bridge
	cmd+="GROUP ALL;\n";
	cmd+="DELETE (>0 0);\n",
	//setup for drawing
	cmd+="CHANGE WIDTH 0.15mm;\n";
	cmd+="LAYER DIMENSION;\n";
	cmd+="GRID mm 0.1;\n";
	cmd+="SET WIRE_BEND 2;\n";

	//Drawing the bridge
	sprintf(cmd,"%sARC CW (%fmm 0mm) (%fmm %dmm) (%fmm %dmm);\n",cmd,((gapWidth+1.0)/2),((gapWidth+1.0)/2),gapWidth,((gapWidth+1.0)/2),gapWidth);
	sprintf(cmd,"%sARC CCW (%fmm 0mm) (%fmm %dmm) (%fmm %dmm);\n",cmd,((gapWidth+1.0)/(-2)),((gapWidth+1.0)/(-2)),gapWidth,((gapWidth+1.0)/(-2)),gapWidth);

	//Drill holes
	cmd+="CHANGE DRILL 0.35mm;\n";

	for(real d=-1.5;d<2;d+=0.5){
		sprintf(cmd,"%sHOLE (%fmm 0mm);\n",cmd,d);
	}
	//saving library 
	cmd+="WRITE '"+lib+"';\n";
	cmd+="CLOSE;\n";//THIS DOES NOT WORK
	cmd+="EDIT '"+brd+"';\n";
	cmd+="USE '"+lib+"';\n";

	int minlengthBridgeX = 20.0;	
	int minlengthBridgeY = 20.0;
	real bridgePosX;
	real bridgePosY;

	//Adding bridges
	for(int l=0;l<wireCount;l++){
		if(!wireRad[l]){
			if(((wireX1[l]-wireX2[l])*cclockwise>0)&&(wireY1[l]==wireY2[l])){
				//upper boarder
				if((wireY1[l]==maxY)||(abs(wireX2[l]-wireX1[l])>minlengthBridgeX)){
					bridgePosY=wireY1[l];

					for(int j = 0;j<=(abs(wireX2[l]-wireX1[l])/minlengthBridgeX);j++){
						bridgePosX=(j+1)/(1+ceil(abs(wireX2[l]-wireX1[l])/minlengthBridgeX));

						if(bridgePosX<1){
							bridgePosX=wireX1[l]+((wireX2[l]-wireX1[l])*bridgePosX);

							deletWirePart((bridgePosX-1.5),bridgePosY,(bridgePosX+1.5),bridgePosY);
							deletWirePart((bridgePosX-1.5),(bridgePosY+gapWidth),(bridgePosX+1.5),(bridgePosY+gapWidth));

							sprintf(cmd,"%sADD 'BRIDG' R0 (%fmm %fmm);\n",cmd,bridgePosX,bridgePosY);
						}
					}
				}														
			}
			else if(((wireX1[l]-wireX2[l])*cclockwise<0)&&(wireY1[l]==wireY2[l])){
				//lower boarder
				if((wireY1[l]==minY)||(abs(wireX2[l]-wireX1[l])>minlengthBridgeX)) {
					bridgePosY=wireY1[l];

					for(int j = 0;j<=(abs(wireX2[l]-wireX1[l])/minlengthBridgeX);j++){
						bridgePosX=(j+1)/(1+ceil(abs(wireX2[l]-wireX1[l])/minlengthBridgeX));

						if(bridgePosX<1){
							bridgePosX=wireX1[l]+((wireX2[l]-wireX1[l])*bridgePosX);

							deletWirePart((bridgePosX-1.5),bridgePosY,(bridgePosX+1.5),bridgePosY);
							deletWirePart((bridgePosX-1.5),(bridgePosY-gapWidth),(bridgePosX+1.5),(bridgePosY-gapWidth));

							sprintf(cmd,"%sADD 'BRIDG' R180 (%fmm %fmm);\n",cmd,bridgePosX,bridgePosY);
						}
					}
				}
			}
			else if(((wireY1[l]-wireY2[l])*cclockwise>0)&&(wireX1[l]==wireX2[l])){
				//right boarder
				if((wireX1[l]==minX)||(abs(wireY2[l]-wireY1[l])>minlengthBridgeY)) {
					bridgePosX=wireX1[l];

					for(int j = 0;j<=(abs(wireY2[l]-wireY1[l])/minlengthBridgeY);j++){
						bridgePosY=(j+1)/(1+ceil(abs(wireY2[l]-wireY1[l])/minlengthBridgeY));

						if(bridgePosY<1){
							bridgePosY=wireY1[l]+((wireY2[l]-wireY1[l])*bridgePosY);

							deletWirePart(bridgePosX,(bridgePosY-1.5),bridgePosX,(bridgePosY+1.5));
							deletWirePart((bridgePosX-gapWidth),(bridgePosY-1.5),(bridgePosX-gapWidth),(bridgePosY+1.5));

							sprintf(cmd,"%sADD 'BRIDG' R90 (%fmm %fmm);\n",cmd,bridgePosX,bridgePosY);
						}
					}
				}
			}
			else {
				//left boarder
				if((wireX1[l]==minX)||(abs(wireY2[l]-wireY1[l])>minlengthBridgeY)) {
					bridgePosX=wireX1[l];

					for(int j = 0;j<=(abs(wireY2[l]-wireY1[l])/minlengthBridgeY);j++){
						bridgePosY=(j+1)/(1+ceil(abs(wireY2[l]-wireY1[l])/minlengthBridgeY));

						if(bridgePosY<1){
							bridgePosY=wireY1[l]+((wireY2[l]-wireY1[l])*bridgePosY);

							deletWirePart(bridgePosX,(bridgePosY-1.5),bridgePosX,(bridgePosY+1.5));
							deletWirePart((bridgePosX+gapWidth),(bridgePosY-1.5),(bridgePosX+gapWidth),(bridgePosY+1.5));

							sprintf(cmd,"%sADD 'BRIDG' R270 (%fmm %fmm);\n",cmd,bridgePosX,bridgePosY);
						}
					}
				}
			}

			//adding miter
			if (potMitX[l])
			{
				//verktors
				real ax, ay, bx, by, cx, cy;
				//angles
				real ab, bc, ac;

				ax = wireX2[l]-wireX1[l];
				ay = wireY2[l]-wireY1[l];

				bx = potMitX[l]-wireX2[l];
				by = potMitY[l]-wireY2[l];

				cx = wireX2[((l+1)%wireCount)]-wireX1[((l+1)%wireCount)];
				cy = wireY2[((l+1)%wireCount)]-wireY1[((l+1)%wireCount)];

				ab=acos((ax * bx + ay * by)/(sqrt(ax * ax + ay * ay) * sqrt(bx * bx + by * by)));
				bc=acos((cx * bx + cy * by)/(sqrt(cx * cx + cy * cy) * sqrt(bx * bx + by * by)));
				//ac=acos((ax * cx + ay * cy)/(sqrt(ax * ax + ay * ay) * sqrt(cx * cx + cy * cy)));

				if(ab<bc){ 
					sprintf(cmd, "%sMITER %d (%fmm %fmm);\n",cmd,gapWidth,potMitX[l],potMitY[l]);
				}
			}
		}
	}

	// ===================				//puts Fiducials in all 4 corners of the panel
	//        Fiducials
	// ===================

	real x_fiducial_left = minX - gapWidth - (panelWidthX/2);
	real x_fiducial_left_max = x_fiducial_left + 0.75;
	real y_fiducial_top = maxY + gapWidth + (panelWidthY/2);
	real y_fiducial_bot = minY - gapWidth - (panelWidthY/2);
	real x_fiducial_right = maxX + gapWidth + (panelWidthX/2);
	real x_fiducial_right_max = x_fiducial_right +0.75;

	real x_fiducial_stop_left = x_fiducial_left - 1.5;
	real x_fiducial_stop_right = x_fiducial_right +1.5;

	// ===================
	//        Top Fiducials
	// ===================

	sprintf(cmd, "%s LAYER TOP;\n", cmd);
	sprintf(cmd, "%s CHANGE WIDTH 0mm;\n", cmd);

	sprintf(cmd, "%s CIRCLE (%fmm %fmm) (%fmm %fmm);\n", cmd, x_fiducial_left, y_fiducial_top, x_fiducial_left_max, y_fiducial_top);
	sprintf(cmd, "%s CIRCLE (%fmm %fmm) (%fmm %fmm);\n", cmd, x_fiducial_left, y_fiducial_bot, x_fiducial_left_max, y_fiducial_bot);
	sprintf(cmd, "%s CIRCLE (%fmm %fmm) (%fmm %fmm);\n", cmd, x_fiducial_right, y_fiducial_top, x_fiducial_right_max, y_fiducial_top);
	sprintf(cmd, "%s CIRCLE (%fmm %fmm) (%fmm %fmm);\n", cmd, x_fiducial_right, y_fiducial_bot, x_fiducial_right_max, y_fiducial_bot);

	sprintf(cmd, "%s LAYER TSTOP;\n", cmd);
	sprintf(cmd, "%s CHANGE WIDTH 0mm;\n", cmd);

	sprintf(cmd, "%s CIRCLE (%fmm %fmm) (%fmm %fmm);\n", cmd, x_fiducial_left, y_fiducial_top, x_fiducial_stop_left, y_fiducial_top);
	sprintf(cmd, "%s CIRCLE (%fmm %fmm) (%fmm %fmm);\n", cmd, x_fiducial_left, y_fiducial_bot, x_fiducial_stop_left, y_fiducial_bot);
	sprintf(cmd, "%s CIRCLE (%fmm %fmm) (%fmm %fmm);\n", cmd, x_fiducial_right, y_fiducial_top, x_fiducial_stop_right, y_fiducial_top);
	sprintf(cmd, "%s CIRCLE (%fmm %fmm) (%fmm %fmm);\n", cmd, x_fiducial_right, y_fiducial_bot, x_fiducial_stop_right, y_fiducial_bot);

	// ===================
	//        Bot Fiducials
	// ===================

	sprintf(cmd, "%s LAYER BOTTOM;\n", cmd);
	sprintf(cmd, "%s CHANGE WIDTH 0mm;\n", cmd);

	sprintf(cmd, "%s CIRCLE (%fmm %fmm) (%fmm %fmm);\n", cmd, x_fiducial_left, y_fiducial_top, x_fiducial_left_max, y_fiducial_top);
	sprintf(cmd, "%s CIRCLE (%fmm %fmm) (%fmm %fmm);\n", cmd, x_fiducial_left, y_fiducial_bot, x_fiducial_left_max, y_fiducial_bot);
	sprintf(cmd, "%s CIRCLE (%fmm %fmm) (%fmm %fmm);\n", cmd, x_fiducial_right, y_fiducial_top, x_fiducial_right_max, y_fiducial_top);
	sprintf(cmd, "%s CIRCLE (%fmm %fmm) (%fmm %fmm);\n", cmd, x_fiducial_right, y_fiducial_bot, x_fiducial_right_max, y_fiducial_bot);

	sprintf(cmd, "%s LAYER BSTOP;\n", cmd);
	sprintf(cmd, "%s CHANGE WIDTH 0mm;\n", cmd);

	sprintf(cmd, "%s CIRCLE (%fmm %fmm) (%fmm %fmm);\n", cmd, x_fiducial_left, y_fiducial_top, x_fiducial_stop_left, y_fiducial_top);
	sprintf(cmd, "%s CIRCLE (%fmm %fmm) (%fmm %fmm);\n", cmd, x_fiducial_left, y_fiducial_bot, x_fiducial_stop_left, y_fiducial_bot);
	sprintf(cmd, "%s CIRCLE (%fmm %fmm) (%fmm %fmm);\n", cmd, x_fiducial_right, y_fiducial_top, x_fiducial_stop_right, y_fiducial_top);
	sprintf(cmd, "%s CIRCLE (%fmm %fmm) (%fmm %fmm);\n", cmd, x_fiducial_right, y_fiducial_bot, x_fiducial_stop_right, y_fiducial_bot);

	// =======================================
	//             Drills Board
	// =======================================
	sprintf(cmd, "%s LAYER HOLES;\n", cmd);

	/*Drills Circuit Board*/
	real circuit_drill_x = minX-4.5;
	real circuit_drill_y_min = minY+5;
	real circuit_drill_y_max = maxY-5;

	sprintf(cmd, "%s CHANGE DRILL 3mm;\n", cmd);
	sprintf(cmd, "%s HOLE (%fmm %fmm);\n", cmd, circuit_drill_x, circuit_drill_y_min);
	sprintf(cmd, "%s HOLE (%fmm %fmm);\n", cmd, circuit_drill_x, circuit_drill_y_max);


	// =================================================
	//             outline Stencil
	// =================================================
	sprintf(cmd, "%s CHANGE WIDTH 0;\n", cmd);

	real x_min_stencil = circuit_drill_x - 49;
	real x_max_stencil = x_max_outline + 48.5;
	real y_min_stencil = y_min_outline -20;
	real y_max_stencil = y_max_outline +20;

	sprintf(cmd, "%s LAYER TCREAM;\n", cmd);
	sprintf(cmd, "%s WIRE (%fmm %fmm) (%fmm %fmm) (%fmm %fmm) (%fmm %fmm) (%fmm %fmm);\n", cmd, x_min_stencil, y_min_stencil, x_max_stencil, y_min_stencil, x_max_stencil, y_max_stencil, x_min_stencil, y_max_stencil, x_min_stencil, y_min_stencil);

	sprintf(cmd, "%s LAYER BCREAM;\n", cmd);
	sprintf(cmd, "%s WIRE (%fmm %fmm) (%fmm %fmm) (%fmm %fmm) (%fmm %fmm) (%fmm %fmm);\n", cmd, x_min_stencil, y_min_stencil, x_max_stencil, y_min_stencil, x_max_stencil, y_max_stencil, x_min_stencil, y_max_stencil, x_min_stencil, y_min_stencil);

	// ========================================
	//             Drills Stencil
	// ========================================
	/*
	Drills als Circles auf tcream- und bcream-Layer
	sonst vom Hersteller nicht berücksichtigt
	tcream, bcream -> für Stencil
	*/
	sprintf(cmd, "%s LAYER TCREAM;\n", cmd);
	sprintf(cmd, "%s GRID mm 1;\n", cmd);
	sprintf(cmd, "%s CHANGE WIDTH 0;\n", cmd);

	real stencil_drill_x_min =circuit_drill_x-30;
	real stencil_drill_x_max = stencil_drill_x_min+2.65;

	sprintf(cmd, "%s CIRCLE (%fmm %fmm) (%fmm %fmm);\n", cmd, stencil_drill_x_min, circuit_drill_y_min, stencil_drill_x_max, circuit_drill_y_min);
	sprintf(cmd, "%s CIRCLE (%fmm %fmm) (%fmm %fmm);\n", cmd, stencil_drill_x_min, circuit_drill_y_max, stencil_drill_x_max, circuit_drill_y_max);

	sprintf(cmd, "%s LAYER BCREAM;\n", cmd);

	sprintf(cmd, "%s CIRCLE (%fmm %fmm) (%fmm %fmm);\n", cmd, stencil_drill_x_min, circuit_drill_y_min, stencil_drill_x_max, circuit_drill_y_min);
	sprintf(cmd, "%s CIRCLE (%fmm %fmm) (%fmm %fmm);\n", cmd, stencil_drill_x_min, circuit_drill_y_max, stencil_drill_x_max, circuit_drill_y_max);

	sprintf(cmd, "%s WRITE;\n", cmd);

	executeAndExit(cmd);
}
