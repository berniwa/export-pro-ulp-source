void executeAndExit(string cmd)
{
	string working_dir = "";
	
	if (schematic)	schematic(S) 	{working_dir = filedir(S.name);} 
	if (board) 		board(B) 		{working_dir = filedir(B.name);} 
	if (library)	library(L) 		{working_dir = filedir(L.name);} 
	
	string scr = working_dir + "tmp.scr";

	output(scr, "w")
	{
		printf("%s", cmd);
	}
	exit(";SCRIPT '" + scr + "';");	
}
