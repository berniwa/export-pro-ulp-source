/************************************************************/
/* HTLExportPro_ImageExport.ulp                             */
/* Exports images of what the PCB will look like            */
/************************************************************/
/* (c) Copyright 2011, Bernhard Wörndl-Aichriedler          */
/* E-Mail: bwa@berniwa.com                                  */
/* Homepage: www.berniwa.com                                */
/************************************************************/
/* Letzte Änderung am 18.02.2011                            */
/* Version 1                                                */
/************************************************************/

#include "Include_FastExecute.ulp";
#include "Include_Misc.ulp";

string getFilename(string basename, string ends_with)
{
	return filesetext(basename,ends_with);
}


void exportImages(int imgExport, int pdfExport, int exportBot, string botImage, string botPdf, int exportTop, string topImage, string topPdf, int resolution, int crop, int mirror, string colorPcb, string colorCopper, string colorSilkscreen, string colorPlating)
{
	string cmd = "";

	string bname = "";
	board(B)
	{
		bname = B.name;
	}

	cmd += "SET PALETTE COLORED;\n";

	cmd += "SET COLOR_LAYER 1 16;\n";
	cmd += "SET COLOR_LAYER 16 17;\n";
	cmd += "SET COLOR_LAYER 17 16;\n";
	cmd += "SET COLOR_LAYER 18 16;\n";
	cmd += "SET COLOR_LAYER 29 18;\n";
	cmd += "SET FILL_LAYER 29 solid;\n";
	cmd += "SET COLOR_LAYER 30 18;\n";
	cmd += "SET FILL_LAYER 30 solid;\n";
	cmd += "SET COLOR_LAYER 124 18;\n";
	cmd += "SET COLOR_LAYER 120 20;\n";
	cmd += "SET COLOR_LAYER 121 21;\n";
	cmd += "SET COLOR_LAYER 122 21;\n";
	cmd += "SET COLOR_LAYER 125 18;\n";
	cmd += "SET COLOR_LAYER 126 18;\n";
	cmd += "SET COLOR_LAYER 127 20;\n";

	cmd += "SET PALETTE 16 " + colorCopper + ";\n";
	cmd += "SET PALETTE 17 " + colorCopper + ";\n";
	cmd += "SET PALETTE 18 " + colorPlating + ";\n";
	cmd += "SET PALETTE 20 0xFF000000;\n";
	cmd += "SET PALETTE 21 " + colorSilkscreen + ";\n";
	cmd += "SET PALETTE 0 " + colorPcb + ";\n";
	cmd += "SET PALETTE 8 0xFFFFFFFF;\n";


	if(EAGLE_VERSION > 5 || (EAGLE_VERSION == 5 && EAGLE_RELEASE >= 11) ) //Support for SET CONFIRM form Eagle 5.11 on
	{
		cmd += "SET CONFIRM YES;\n";
	}

	if(exportTop)
	{
		cmd += "DISPLAY NONE;DISPLAY 1 18 29 121 123 124 125 127 ;\n";
		if (imgExport) {
			sprintf(cmd, "%s EXPORT IMAGE '%s' %d;\n", cmd, topImage, resolution);
		}
		if (pdfExport) {
			cmd += "PRINT SHEETS ALL HIERARCHY PAPER A4 portrait FILE '" + topPdf + "';\n";
		}
	}
	if(exportBot)
	{
		cmd += "DISPLAY NONE;DISPLAY 16 18 30 122 123 124 126 127;\n";
		if (imgExport) {
			sprintf(cmd, "%s EXPORT IMAGE '%s' %d;\n", cmd, botImage, resolution);
		}
		if (pdfExport) {
			cmd += "PRINT SHEETS ALL HIERARCHY PAPER A4 portrait FILE '" + botPdf + "';\n";
		}
	}


	if(EAGLE_VERSION > 5 || (EAGLE_VERSION == 5 && EAGLE_RELEASE >= 11) ) //Support for SET CONFIRM form Eagle 5.11 on
	{
		cmd += "SET CONFIRM NO;\n";
	}

	cmd += "SET PALETTE 0 0xFFFFFFFF;\n";

	cmd += "SET COLOR_LAYER 1 4;\n";
	cmd += "SET COLOR_LAYER 16 1;\n";
	cmd += "SET COLOR_LAYER 17 2;\n";
	cmd += "SET COLOR_LAYER 18 2;\n";
	

	string layers = "";

	board(B)
	{
		
		B.layers(L)
		{
			if(L.visible)
			{
				sprintf(layers, layers + " %d", L.number);
			}
		}
	}

	cmd += "DISPLAY NONE; DISPLAY " + layers + ";\n";

	if(palette(-1) == PALETTE_BLACK)
	{
		cmd += "SET PALETTE BLACK;\n";
	}
	else if(palette(-1) == PALETTE_WHITE)
	{
		cmd += "SET PALETTE WHITE;\n";
	}
	else
	{
		cmd += "SET PALETTE COLORED;\n";
	}

	cmd += "SET FILL_LAYER 29 LtSlash;\n";
	cmd += "SET FILL_LAYER 30 BkSlash;\n";
	
	if(exportBot && crop && imgExport)
	{
		sprintf(cmd, "%s RUN %sCropColor.ulp '%s' %d '%s';\n", cmd, getUlpDir("Include_"), botImage, resolution,filesetext(bname,".bat"));
	}
	if(exportTop && crop && imgExport)
	{
		sprintf(cmd, "%s RUN %sCropColor.ulp '%s' %d '%s';\n", cmd, getUlpDir("Include_"), topImage, resolution,filesetext(bname,".bat"));
	}

	if(exportBot && mirror && imgExport)
	{
		sprintf(cmd, "%s RUN %sMirrorColor.ulp '%s' '%s';\n", cmd, getUlpDir("Include_"), botImage,filesetext(bname,".bat"));
	}	
	
	executeAndExit(cmd);
}


exportImages(strtol(argv[12]),strtol(argv[13]),strtol(argv[2]),argv[1],argv[14],strtol(argv[4]),argv[3],argv[15],strtol(argv[5]),strtol(argv[6]),strtol(argv[7]), argv[8], argv[9], argv[10], argv[11]);
